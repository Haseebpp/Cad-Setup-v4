;;; ==========================================================================
;;; 01_Workflow-Keys.lsp - Numbered Rapid Workflow Keys (1, 2, 3, 4, 5...)
;;; Layer: Commands (Priority 01)
;;; Author   : Haseeb
;;; ==========================================================================
;;;
;;; SUMMARY:
;;;   Provides ergonomic single-digit drafting shortcuts (1, 2, 3, 4, 5...) with
;;;   dual-mode operation:
;;;     1. NO SELECTION: Automatic layer creation, target layer isolation/switching,
;;;        and drafting tools (PL, REC, Grid, Viewport, Construction lines).
;;;     2. SELECTION ACTIVE (Pickfirst): Instantly reassigns all selected entities
;;;        to the chosen target layer (Keys 1-3 to dedicated layers, Keys 4-7 & `
;;;        to category/R-layer lists via prompt/dialog), preserving CLAYER and
;;;        retaining active selection for immediate follow-up commands (Move, Copy, Scale, etc.).
;;;
;;; KEY MAPPINGS:
;;;   [0] / L0 / BY0 : Layer 0 & ByLayer Normalizer (Dual-mode, Deep Block recursion, Drawing Defaults)
;;;   [1] / HL : Help Line & Guide Points (HLMODE 0=Points, 1=Lines [Default], 2=Xlines)
;;;   [1M] / HLMODE / HLM : Switch Help Line generation mode (0, 1, 2) & instantly refresh layer
;;;   [1X] : Rapid toggle between HLMODE 1 (Line Segments) and 2 (Infinite Xlines)
;;;   [XX] : Direct Help Line with Infinite Xlines (sets HLMODE=2 and launches HL)
;;;   [2] / VP : Viewport Boundary (Draws frame on "02-VIEW-PORT" / Reassigns selection to "02-VIEW-PORT")
;;;   [3] / GL : Grid Line & System Generator (DCL grid maker / Reassigns selection to "03-GRID-LINE")
;;;   [4] / LL : Line Layer (Interactive DCL selector / Reassigns selection to R-LINE-* layer)
;;;   [5] / ML : Material Layer (Interactive DCL selector / Reassigns selection to R-MAT-* layer)
;;;   [6] / AD : Annotation & Dim Suite (Interactive DCL selector / Reassigns selection to R-ANNO-* layer)
;;;   [7] / HD : Fittings & Hardware (Interactive DCL selector / Reassigns selection to R-HARD-* layer)
;;;   [8] / BL : Blocks & Components (Visual DCL insertion palette for standard joinery blocks)
;;;   [-] / R- : R-Layer Selector (Interactive DCL inspector / Reassigns selection to R-* layer)
;;;
;;; ==========================================================================

(vl-load-com)

;;; --------------------------------------------------------------------------
;;; 0. WORKFLOW LAYER CONFIGURATION
;;; --------------------------------------------------------------------------
(setq *WF-LAYER-HL* "01-HELP-LINE")     ;; Key 1: Construction / Help Line
(setq *WF-LAYER-VP* "02-VIEW-PORT")     ;; Key 2: Viewport Boundary & Metadata
(setq *WF-LAYER-GL* "03-GRID-LINE")     ;; Key 3: Structural / Layout Grid Line
(setq *WF-LAYER-LL* nil)                ;; Key 4: Active Line Layer (set dynamically)
(setq *WF-LAYER-ML* nil)                ;; Key 5: Active Material Layer (set dynamically)
(setq *WF-LAYER-AD* nil)                ;; Key 6: Active Annotation Layer (set dynamically)
(setq *WF-LAYER-HD* nil)                ;; Key 7: Active Hardware Layer (set dynamically)
(setq *WF-LAYER-RL* nil)                ;; Key -: Active R-Layer (set dynamically)
(setq *WF-TOOL-RL* "Polyline")          ;; Key -: Default drawing tool ("Polyline" or "Rectangle")

;; Help Line Generation Mode (HLMODE):
;;   0 = Only Guide Points visible (clears all lines and xlines)
;;   1 = Line Segments through collinear guide points (Default)
;;   2 = Infinite Xlines through collinear guide points
(if (null *HLMODE*) (setq *HLMODE* 1))
(setq *HL-TOL* 0.001)                   ;; 1 micron coordinate tolerance for collinear detection


;;; --------------------------------------------------------------------------
;;; 1. HELP LINE / GUIDE POINT NODE ENGINE (1 / HL / HLMODE / HLM / 1M)
;;; --------------------------------------------------------------------------
(vl-load-com)

;;; Low-level entity creation helpers (translating UCS -> WCS)
(defun CadSetup:HL-MkPoint (pt lay / ptWCS)
  (setq ptWCS (trans pt 1 0))
  (entmake
    (list
      '(0 . "POINT")
      (cons 8 lay)
      (cons 10 ptWCS)
    )
  )
  (entlast)
)

(defun CadSetup:HL-MkLine (p1 p2 lay / p1WCS p2WCS)
  (setq p1WCS (trans p1 1 0)
        p2WCS (trans p2 1 0))
  (entmake
    (list
      '(0 . "LINE")
      (cons 8 lay)
      (cons 10 p1WCS)
      (cons 11 p2WCS)
    )
  )
  (entlast)
)

(defun CadSetup:HL-MkXLine (pt dir lay / basePt dirVec res acadApp doc ms obj)
  (setq basePt (trans pt 1 0)
        dirVec (trans dir 1 0 T))
  (setq res (vl-catch-all-apply
              'entmake
              (list
                (list
                  '(0 . "XLINE")
                  '(100 . "AcDbEntity")
                  (cons 8 lay)
                  '(100 . "AcDbXline")
                  (cons 10 basePt)
                  (cons 11 dirVec)
                )
              )))
  (if (or (vl-catch-all-error-p res) (not res))
    ;; Robust fallback to ActiveX if entmake fails
    (progn
      (setq acadApp (vlax-get-acad-object)
            doc     (if acadApp (vla-get-activedocument acadApp))
            ms      (if doc (vla-get-modelspace doc)))
      (if ms
        (progn
          (setq obj (vl-catch-all-apply
                      'vla-addxline
                      (list ms
                            (vlax-3d-point basePt)
                            (vlax-3d-point (mapcar '+ basePt dirVec)))))
          (if (and (not (vl-catch-all-error-p obj)) (= (type obj) 'VLA-OBJECT))
            (progn
              (vla-put-layer obj lay)
              (vlax-vla-object->ename obj)
            )
            nil
          )
        )
        nil
      )
    )
    (entlast)
  )
)

;;; Helper: Group points that share a coordinate within tolerance
;;; coordIdx: 0 for X, 1 for Y
(defun CadSetup:HL-GroupCollinear (pts coordIdx tol / sorted groups curGroup curCoord p val)
  (if (and pts (> (length pts) 1))
    (progn
      ;; Sort points ascending along the target axis
      (setq sorted (vl-sort (append pts nil)
                            (function (lambda (a b)
                                        (< (nth coordIdx a) (nth coordIdx b))))))
      (setq groups   nil
            curGroup nil
            curCoord nil)
      (foreach p sorted
        (setq val (nth coordIdx p))
        (if (null curGroup)
          (setq curGroup (list p)
                curCoord val)
          (if (<= (abs (- val curCoord)) tol)
            (setq curGroup (cons p curGroup))
            (progn
              (if (> (length curGroup) 1)
                (setq groups (cons (reverse curGroup) groups))
              )
              (setq curGroup (list p)
                    curCoord val)
            )
          )
        )
      )
      (if (and curGroup (> (length curGroup) 1))
        (setq groups (cons (reverse curGroup) groups))
      )
      (reverse groups)
    )
    nil
  )
)

;;; Helper: De-duplicate points within tolerance
(defun CadSetup:HL-DeduplicatePoints (pts tol / unique p)
  (setq unique nil)
  (foreach p pts
    (if (not (vl-some (function (lambda (u) (equal p u tol))) unique))
      (setq unique (cons p unique))
    )
  )
  (reverse unique)
)

;;; Helper: Delete all LINE and XLINE entities on target layer
(defun CadSetup:HL-ClearLines (lay / ssOld i ent)
  (if (and lay (tblsearch "LAYER" lay))
    (progn
      (setq ssOld (ssget "_X" (list '(0 . "LINE,XLINE") (cons 8 lay))))
      (if ssOld
        (repeat (setq i (sslength ssOld))
          (setq ent (ssname ssOld (setq i (1- i))))
          (vl-catch-all-apply 'entdel (list ent))
        )
      )
    )
  )
)

;;; Helper: Read all points on target layer (in UCS)
(defun CadSetup:HL-GetPoints (lay / ssPts i ent ed ptWCS ptUCS pts)
  (setq pts nil)
  (if (and lay (tblsearch "LAYER" lay))
    (progn
      (setq ssPts (ssget "_X" (list '(0 . "POINT") (cons 8 lay))))
      (if ssPts
        (repeat (setq i (sslength ssPts))
          (setq ent   (ssname ssPts (setq i (1- i)))
                ed    (entget ent)
                ptWCS (cdr (assoc 10 ed))
                ptUCS (trans ptWCS 0 1))
          (setq pts (cons ptUCS pts))
        )
      )
    )
  )
  pts
)

;;; Core Solver Engine: Solves and rebuilds Help Layer geometry from guide points
(defun CadSetup:HL-SolveLayer (lay / *error* ssPts i ent ed ptWCS ptUCS pts
                                   tol hGroups vGroups grp grpCoord sortedGrp
                                   idx p1 p2)
  (defun *error* (msg)
    (if (and msg (not (wcmatch (strcase msg t) "*break*,*cancel*,*exit*")))
      (princ (strcat "\n[HL-Solve] Error: " msg))
    )
    (princ)
  )

  (if (null lay) (setq lay (if *WF-LAYER-HL* *WF-LAYER-HL* "01-HELP-LINE")))
  (if (null *HLMODE*) (setq *HLMODE* 1))
  (setq tol (if *HL-TOL* *HL-TOL* 0.001))

  ;; Ensure target layer is unlocked, thawed, and turned ON
  (if (boundp 'CadSetup:EnsureLayerReady)
    (CadSetup:EnsureLayerReady lay)
  )

  ;; 1. Clean Refresh: Always remove all existing LINE and XLINE entities on layer
  (CadSetup:HL-ClearLines lay)

  ;; 2. If mode is 0 (Points Only), we stop here; only points remain visible
  (if (= *HLMODE* 0)
    (princ)
    (progn
      ;; 3. Collect all POINT entities on layer (translated from WCS -> UCS)
      (setq pts (CadSetup:HL-GetPoints lay))

      (if (and pts (> (length pts) 1))
        (progn
          ;; De-duplicate point coordinates
          (setq pts (CadSetup:HL-DeduplicatePoints pts tol))

          ;; -------------------------------------------------------------
          ;; 4. Horizontal Collinear Groups (sharing Y coordinate in UCS)
          ;; -------------------------------------------------------------
          (setq hGroups (CadSetup:HL-GroupCollinear pts 1 tol))
          (foreach grp hGroups
            (setq grpCoord  (cadr (car grp)) ;; Canonical Y
                  sortedGrp (vl-sort (append grp nil)
                                     (function (lambda (a b) (< (car a) (car b))))))
            ;; De-duplicate X values within the horizontal group
            (setq sortedGrp (CadSetup:HL-DeduplicatePoints sortedGrp tol))
            (if (>= (length sortedGrp) 2)
              (cond
                ;; Mode 1: Segment by segment between adjacent consecutive points
                ((= *HLMODE* 1)
                 (setq idx 0)
                 (while (< idx (1- (length sortedGrp)))
                   (setq p1 (nth idx sortedGrp)
                         p2 (nth (1+ idx) sortedGrp))
                   (if (> (- (car p2) (car p1)) tol)
                     (CadSetup:HL-MkLine
                       (list (car p1) grpCoord (caddr p1))
                       (list (car p2) grpCoord (caddr p2))
                       lay
                     )
                   )
                   (setq idx (1+ idx))
                 )
                )
                ;; Mode 2: Infinite horizontal Xline through the collinear row
                ((= *HLMODE* 2)
                 (CadSetup:HL-MkXLine
                   (list (car (car sortedGrp)) grpCoord (caddr (car sortedGrp)))
                   '(1.0 0.0 0.0)
                   lay
                 )
                )
              )
            )
          )

          ;; -------------------------------------------------------------
          ;; 5. Vertical Collinear Groups (sharing X coordinate in UCS)
          ;; -------------------------------------------------------------
          (setq vGroups (CadSetup:HL-GroupCollinear pts 0 tol))
          (foreach grp vGroups
            (setq grpCoord  (car (car grp)) ;; Canonical X
                  sortedGrp (vl-sort (append grp nil)
                                     (function (lambda (a b) (< (cadr a) (cadr b))))))
            ;; De-duplicate Y values within the vertical group
            (setq sortedGrp (CadSetup:HL-DeduplicatePoints sortedGrp tol))
            (if (>= (length sortedGrp) 2)
              (cond
                ;; Mode 1: Segment by segment between adjacent consecutive points
                ((= *HLMODE* 1)
                 (setq idx 0)
                 (while (< idx (1- (length sortedGrp)))
                   (setq p1 (nth idx sortedGrp)
                         p2 (nth (1+ idx) sortedGrp))
                   (if (> (- (cadr p2) (cadr p1)) tol)
                     (CadSetup:HL-MkLine
                       (list grpCoord (cadr p1) (caddr p1))
                       (list grpCoord (cadr p2) (caddr p2))
                       lay
                     )
                   )
                   (setq idx (1+ idx))
                 )
                )
                ;; Mode 2: Infinite vertical Xline through the collinear column
                ((= *HLMODE* 2)
                 (CadSetup:HL-MkXLine
                   (list grpCoord (cadr (car sortedGrp)) (caddr (car sortedGrp)))
                   '(0.0 1.0 0.0)
                   lay
                 )
                )
              )
            )
          )
        )
      )
    )
  )
  (princ)
)

;;; Helper: Extract vertices/endpoints from pre-selected entities into guide points
(defun CadSetup:HL-ExtractVertices (ss lay / *error* i ent ed eType obj pts p1 p2 elev
                                              vEnt tol count existPts ePt)
  (defun *error* (msg)
    (if (and msg (not (wcmatch (strcase msg t) "*break*,*cancel*,*exit*")))
      (princ (strcat "\n[HL-Extract] Error: " msg))
    )
    (princ)
  )

  (if (null lay) (setq lay (if *WF-LAYER-HL* *WF-LAYER-HL* "01-HELP-LINE")))
  (setq tol (if *HL-TOL* *HL-TOL* 0.001))

  ;; Ensure target layer is ready
  (if (boundp 'CadSetup:EnsureLayerReady)
    (CadSetup:EnsureLayerReady lay)
  )

  ;; Cache existing points on layer to avoid duplicates
  (setq existPts (CadSetup:HL-GetPoints lay))

  (setq pts   nil
        count 0)

  (if (and ss (> (sslength ss) 0))
    (progn
      (repeat (setq i (sslength ss))
        (setq ent   (ssname ss (setq i (1- i)))
              ed    (entget ent)
              eType (cdr (assoc 0 ed)))

        (cond
          ;; 1. LINE entity
          ((= eType "LINE")
           (setq p1 (trans (cdr (assoc 10 ed)) 0 1)
                 p2 (trans (cdr (assoc 11 ed)) 0 1)
                 pts (cons p1 (cons p2 pts)))
           (vl-catch-all-apply 'entdel (list ent))
          )

          ;; 2. LWPOLYLINE entity
          ((= eType "LWPOLYLINE")
           (setq elev (cdr (assoc 38 ed)))
           (if (null elev) (setq elev 0.0))
           (foreach item ed
             (if (= (car item) 10)
               (setq p1 (trans (trans (list (cadr item) (caddr item) elev) ent 0) 0 1)
                     pts (cons p1 pts))
             )
           )
           (vl-catch-all-apply 'entdel (list ent))
          )

          ;; 3. Legacy 2D / 3D POLYLINE
          ((= eType "POLYLINE")
           (setq vEnt (entnext ent))
           (while (and vEnt (/= (cdr (assoc 0 (entget vEnt))) "SEQEND"))
             (setq p1 (trans (cdr (assoc 10 (entget vEnt))) 0 1)
                   pts (cons p1 pts)
                   vEnt (entnext vEnt))
           )
           (vl-catch-all-apply 'entdel (list ent))
          )

          ;; 4. POINT entity
          ((= eType "POINT")
           (setq p1 (trans (cdr (assoc 10 ed)) 0 1)
                 pts (cons p1 pts))
           ;; If not already on lay, delete from other layer
           (if (/= (strcase (cdr (assoc 8 ed))) (strcase lay))
             (vl-catch-all-apply 'entdel (list ent))
           )
          )

          ;; 5. ARC or CIRCLE
          ((or (= eType "ARC") (= eType "CIRCLE"))
           (setq p1 (trans (cdr (assoc 10 ed)) 0 1)
                 pts (cons p1 pts))
           (if (= eType "ARC")
             (progn
               (setq obj (vl-catch-all-apply 'vlax-ename->vla-object (list ent)))
               (if (and (not (vl-catch-all-error-p obj)) (= (type obj) 'VLA-OBJECT))
                 (setq pts (cons (trans (vlax-curve-getstartpoint obj) 0 1)
                           (cons (trans (vlax-curve-getendpoint obj) 0 1) pts)))
               )
             )
           )
           (vl-catch-all-apply 'entdel (list ent))
          )

          ;; 6. Generic Curve fallback (Spline, Ellipse, etc.)
          ((wcmatch eType "SPLINE,ELLIPSE")
           (setq obj (vl-catch-all-apply 'vlax-ename->vla-object (list ent)))
           (if (and (not (vl-catch-all-error-p obj)) (= (type obj) 'VLA-OBJECT))
             (setq pts (cons (trans (vlax-curve-getstartpoint obj) 0 1)
                       (cons (trans (vlax-curve-getendpoint obj) 0 1) pts)))
           )
           (vl-catch-all-apply 'entdel (list ent))
          )
        )
      )

      ;; De-duplicate extracted points
      (setq pts (CadSetup:HL-DeduplicatePoints pts tol))

      ;; Create POINT entities on target layer for points not already present
      (foreach p1 pts
        (if (not (vl-some (function (lambda (ex) (equal p1 ex tol))) existPts))
          (progn
            (CadSetup:HL-MkPoint p1 lay)
            (setq existPts (cons p1 existPts)
                  count    (1+ count))
          )
        )
      )

      ;; Re-solve layer according to active HLMODE
      (CadSetup:HL-SolveLayer lay)
      (princ (strcat "\n[HL] Extracted " (itoa count) " new guide points to " lay
                     " and solved geometry (HLMODE = " (itoa *HLMODE*) ")."))
    )
  )
  count
)

;;; --------------------------------------------------------------------------
;;; HLMODE COMMAND & SHORTCUTS (HLMODE / HLM / 1M)
;;; --------------------------------------------------------------------------
(defun c:HLMODE ( / curMode input newMode lay desc )
  (if (null *HLMODE*) (setq *HLMODE* 1))
  (setq curMode *HLMODE*
        lay     (if *WF-LAYER-HL* *WF-LAYER-HL* "01-HELP-LINE"))

  (setq desc (cond ((= curMode 0) "0 (Only Points)")
                   ((= curMode 1) "1 (Line Segments)")
                   ((= curMode 2) "2 (Infinite Xlines)")
                   (t (itoa curMode))))
  (princ (strcat "\nCurrent Help Line Mode: " desc))

  (initget "0 1 2 Points Lines Xlines")
  (setq input (getkword (strcat "\nEnter Help Line Mode [0=Points / 1=Lines / 2=Xlines] <" (itoa curMode) ">: ")))

  (cond
    ((or (= input "0") (= input "Points")) (setq newMode 0))
    ((or (= input "1") (= input "Lines"))  (setq newMode 1))
    ((or (= input "2") (= input "Xlines")) (setq newMode 2))
    ((or (null input) (= input ""))        (setq newMode curMode))
    (t (setq newMode curMode))
  )

  (setq *HLMODE* newMode)
  (if (boundp 'CadSetup:UndoStart) (CadSetup:UndoStart))
  (CadSetup:HL-SolveLayer lay)
  (if (boundp 'CadSetup:UndoEnd) (CadSetup:UndoEnd))

  (setq desc (cond ((= *HLMODE* 0) "0 (Only Points)")
                   ((= *HLMODE* 1) "1 (Line Segments)")
                   ((= *HLMODE* 2) "2 (Infinite Xlines)")
                   (t (itoa *HLMODE*))))
  (princ (strcat "\n[HLMODE] Mode set to " desc ". \"" lay "\" refreshed successfully."))
  (princ)
)

(defun c:HLM () (c:HLMODE))
(defun c:1M  () (c:HLMODE))

;;; TOGGLE-HLMODE-1-2 (1X): Rapid toggle between Mode 1 (Lines) and Mode 2 (Xlines)
(defun c:TOGGLE-HLMODE-1-2 ( / lay desc )
  (if (null *HLMODE*) (setq *HLMODE* 1))
  ;; If in Mode 2, toggle to 1; if in Mode 1 or 0, toggle to 2 (or 1 if 0)
  (setq *HLMODE* (cond ((= *HLMODE* 2) 1)
                       ((= *HLMODE* 1) 2)
                       (t 1))
        lay      (if *WF-LAYER-HL* *WF-LAYER-HL* "01-HELP-LINE"))
  (if (boundp 'CadSetup:UndoStart) (CadSetup:UndoStart))
  (CadSetup:HL-SolveLayer lay)
  (if (boundp 'CadSetup:UndoEnd) (CadSetup:UndoEnd))
  (setq desc (if (= *HLMODE* 2) "2 (Infinite Xlines)" "1 (Line Segments)"))
  (princ (strcat "\n[1X] HLMODE toggled to " desc ". \"" lay "\" refreshed successfully."))
  (princ)
)

(defun c:1X () (c:TOGGLE-HLMODE-1-2))

;;; HL-XLINES (XX): Set HLMODE to 2 (Infinite Xlines) and launch HL drafting
(defun c:HL-XLINES ( / lay )
  (setq *HLMODE* 2
        lay      (if *WF-LAYER-HL* *WF-LAYER-HL* "01-HELP-LINE"))
  (if (boundp 'CadSetup:HL-SolveLayer)
    (CadSetup:HL-SolveLayer lay)
  )
  (princ "\n[XX] HLMODE set to 2 (Infinite Xlines).")
  (c:HL)
  (princ)
)

(defun c:XX () (c:HL-XLINES))

;;; --------------------------------------------------------------------------
;;; MAIN WORKFLOW COMMAND: 1 / HL
;;; --------------------------------------------------------------------------
(defun c:HL ( / ss *error* oldLayer oldEcho lay pt1 pt2 history top
                pEnt promptStr _solveNow )
  (setq ss  (ssget "_I")
        lay (if *WF-LAYER-HL* *WF-LAYER-HL* "01-HELP-LINE"))
  (if (null *HLMODE*) (setq *HLMODE* 1))

  ;; 1. SELECTION ACTIVE (Pickfirst): Extract vertices into guide points & solve
  (if (and ss (> (sslength ss) 0))
    (progn
      (if (boundp 'CadSetup:UndoStart) (CadSetup:UndoStart))
      (CadSetup:HL-ExtractVertices ss lay)
      (if (boundp 'CadSetup:UndoEnd) (CadSetup:UndoEnd))
      (princ)
    )
    ;; 2. NO SELECTION: Interactive guide point node drafting with live solver
    (progn
      (defun *error* (msg)
        (if oldEcho  (setvar "CMDECHO" oldEcho))
        (if oldLayer (setvar "CLAYER" oldLayer))
        (if (boundp 'CadSetup:UndoReset) (CadSetup:UndoReset))
        (if (and msg (not (wcmatch (strcase msg t) "*break*,*cancel*,*exit*")))
          (princ (strcat "\n[HL] Error: " msg))
        )
        (princ)
      )

      (defun _solveNow ()
        (CadSetup:HL-SolveLayer lay)
      )

      (setq oldEcho  (getvar "CMDECHO")
            oldLayer (getvar "CLAYER"))
      (setvar "CMDECHO" 0)

      (if (boundp 'CadSetup:UndoStart) (CadSetup:UndoStart))

      ;; Safely ensure and set current layer to 01-HELP-LINE
      (CadSetup:SetCurrentLayerSafe lay)

      ;; Prompt for first guide point (with Mode switch option)
      (initget "Mode")
      (setq pt1 (getpoint (strcat "\n[HLMODE=" (itoa *HLMODE*) "] Specify first guide point or [Mode]: ")))
      (while (= pt1 "Mode")
        (c:HLMODE)
        (initget "Mode")
        (setq pt1 (getpoint (strcat "\n[HLMODE=" (itoa *HLMODE*) "] Specify first guide point or [Mode]: ")))
      )

      (if (listp pt1)
        (progn
          ;; Place point node for first click
          (setq pEnt    (CadSetup:HL-MkPoint pt1 lay)
                history (list (list pEnt pt1)))
          (_solveNow)

          ;; Interactive loop for subsequent guide points
          (while pt1
            (if (> (length history) 1)
              (initget "Mode Undo Close")
              (initget "Mode Undo")
            )
            (setq promptStr (strcat "\n[HLMODE=" (itoa *HLMODE*)
                                    "] Specify next guide point or ["
                                    (if (> (length history) 1) "Mode/Undo/Close" "Mode/Undo")
                                    "]: "))
            (setq pt2 (getpoint pt1 promptStr))

            (cond
              ;; Switch HLMODE mid-command
              ((= pt2 "Mode")
               (c:HLMODE)
               ;; pt1 remains active at the same node
              )

              ;; Undo handling: delete last placed point entity and re-solve
              ((= pt2 "Undo")
               (setq top     (car history)
                     history (cdr history))
               (if (car top)
                 (vl-catch-all-apply 'entdel (list (car top)))
               )
               (_solveNow)
               (if history
                 (setq pt1 (cadr (car history)))
                 (progn
                   ;; All session points undone; prompt for first point again
                   (initget "Mode")
                   (setq pt1 (getpoint (strcat "\n[HLMODE=" (itoa *HLMODE*) "] Specify first guide point or [Mode]: ")))
                   (while (= pt1 "Mode")
                     (c:HLMODE)
                     (initget "Mode")
                     (setq pt1 (getpoint (strcat "\n[HLMODE=" (itoa *HLMODE*) "] Specify first guide point or [Mode]: ")))
                   )
                   (if (listp pt1)
                     (progn
                       (setq pEnt    (CadSetup:HL-MkPoint pt1 lay)
                             history (list (list pEnt pt1)))
                       (_solveNow)
                     )
                   )
                 )
               )
              )

              ;; Close handling: cleanly finish
              ((= pt2 "Close")
               (setq pt1 nil)
              )

              ;; User clicked next guide point
              ((listp pt2)
               (setq pEnt    (CadSetup:HL-MkPoint pt2 lay)
                     history (cons (list pEnt pt2) history)
                     pt1     pt2)
               (_solveNow)
              )

              ;; Enter / Space / nil / Esc to exit
              (t
               (setq pt1 nil)
              )
            )
          )
        )
      )

      (setvar "CLAYER" oldLayer)
      (if (boundp 'CadSetup:UndoEnd) (CadSetup:UndoEnd))
      (setvar "CMDECHO" oldEcho)

      (princ (strcat "\n[HL] Completed (HLMODE=" (itoa *HLMODE*) "). Restored layer: " oldLayer))
      (princ)
    )
  )
)

(defun c:1 () (c:HL))


;;; --------------------------------------------------------------------------
;;; 2. VIEWPORT BOUNDARY & METADATA TAGGER (2 / VP)
;;; --------------------------------------------------------------------------
(defun c:VP ( / ss *error* oldLayer oldEcho lastEnt newEnt bbox
                oldDimScale oldDimClrd oldDimClre oldDimClrt oldDimBlk
                oldDimAsz oldDimTad oldDimTxt oldDimDec oldDimZin oldDimTxSty
                p1 p2 w h sc th offsetIn insInX insInY
                vpName cdate dotPos dPart tPart dtStr areaStr ratioStr scVal refScStr
                midPt lay dimLay dimOff ptTop1 ptTop2 ptTopDim ptRt1 ptRt2 ptRtDim )

  (setq ss (ssget "_I"))
  (setq lay (if *WF-LAYER-VP* *WF-LAYER-VP* "02-VIEW-PORT"))

  (if (and ss (> (sslength ss) 0))
    (progn
      (CadSetup:AssignEntitiesToLayer ss lay)
      (princ)
    )
    (progn
      (setq oldEcho     (getvar "CMDECHO")
        oldLayer    (getvar "CLAYER")
        oldDimScale (getvar "DIMSCALE")
        oldDimClrd  (getvar "DIMCLRD")
        oldDimClre  (getvar "DIMCLRE")
        oldDimClrt  (getvar "DIMCLRT")
        oldDimBlk   (getvar "DIMBLK")
        oldDimAsz   (getvar "DIMASZ")
        oldDimTad   (getvar "DIMTAD")
        oldDimTxt   (getvar "DIMTXT")
        oldDimDec   (getvar "DIMDEC")
        oldDimZin   (getvar "DIMZIN")
        oldDimTxSty (getvar "DIMTXSTY"))

  (defun *error* (msg)
    (if oldEcho (setvar "CMDECHO" oldEcho))
    (if oldLayer 
      (progn
        (setvar "CLAYER" oldLayer)
        (princ (strcat "\n[VP] Restored layer: " oldLayer))
      )
    )
    (if oldDimScale (setvar "DIMSCALE" oldDimScale))
    (if oldDimClrd  (setvar "DIMCLRD"  oldDimClrd))
    (if oldDimClre  (setvar "DIMCLRE"  oldDimClre))
    (if oldDimClrt  (setvar "DIMCLRT"  oldDimClrt))
    (if oldDimBlk
      (if (= oldDimBlk "") (setvar "DIMBLK" ".") (setvar "DIMBLK" oldDimBlk))
    )
    (if oldDimAsz   (setvar "DIMASZ"   oldDimAsz))
    (if oldDimTad   (setvar "DIMTAD"   oldDimTad))
    (if oldDimTxt   (setvar "DIMTXT"   oldDimTxt))
    (if oldDimDec   (setvar "DIMDEC"   oldDimDec))
    (if oldDimZin   (setvar "DIMZIN"   oldDimZin))
    (if oldDimTxSty (setvar "DIMTXSTY" oldDimTxSty))
    (if (boundp 'CadSetup:UndoReset) (CadSetup:UndoReset))
    (if (and msg (not (wcmatch (strcase msg t) "*break*,*cancel*,*exit*")))
      (princ (strcat "\n[VP] Error: " msg))
    )
    (princ)
  )

  (setvar "CMDECHO" 0)
  (if (boundp 'CadSetup:UndoStart) (CadSetup:UndoStart))

  (CadSetup:SetCurrentLayerSafe lay)

  (setq lastEnt (entlast))

  (setvar "CMDECHO" 1)
  (initcommandversion)
  (command "._rectang")
  (while (> (getvar "CMDACTIVE") 0)
    (command pause)
  )
  (setvar "CMDECHO" 0)

  (setq newEnt (entlast))
  (if (and newEnt (not (eq lastEnt newEnt)))
    (progn
      (setq bbox (CadSetup:GetBoundingBox (vlax-ename->vla-object newEnt)))
      (if bbox
        (progn
          (setq p1 (car bbox)
                p2 (cadr bbox))

          (setq w (abs (- (car p2) (car p1)))
                h (abs (- (cadr p2) (cadr p1))))

          (if (and (> w 0.0) (> h 0.0))
            (progn
              ;; 1. Prompt for Viewport Title
              (setq vpName (getstring t "\nEnter Viewport Name <VIEW PORT>: "))
              (if (or (null vpName) (= vpName ""))
                (setq vpName "VIEW PORT")
              )

              ;; 2. A3 Dynamic Scale Calculation (ISO A3 = 420 x 297 mm)
              (if (>= w h)
                (setq sc (max (/ w 420.0) (/ h 297.0)))
                (setq sc (max (/ w 297.0) (/ h 420.0)))
              )
              (if (< sc 1.0) (setq sc 1.0))

              (setq th (* sc 3.0))

              ;; 3. Metadata Computations
              (setq cdate (rtos (getvar "CDATE") 2 6))
              (setq dotPos (vl-string-search "." cdate))
              (if dotPos
                (progn
                  (setq dPart (substr cdate 1 dotPos)
                        tPart (substr cdate (+ dotPos 2)))
                  (while (< (strlen tPart) 4) (setq tPart (strcat tPart "0")))
                  (setq dtStr (strcat (substr dPart 1 4) "-" (substr dPart 5 2) "-" (substr dPart 7 2)
                                      "  " (substr tPart 1 2) ":" (substr tPart 3 2)))
                )
                (setq dtStr (substr cdate 1 10))
              )

              (setq areaStr  (rtos (/ (* w h) 1000000.0) 2 2))
              (setq ratioStr (rtos (/ w h) 2 2))

              (setq scVal    (fix (+ 0.5 sc)))
              (if (< scVal 1) (setq scVal 1))
              (setq refScStr (itoa scVal))

              ;; 4. Inside Block Tag (Consolidated Bottom-Left, Vibrant Pro Multi-Color Palette)
              (setq offsetIn (* th 1.2)
                    insInX   (+ (car p1) offsetIn)
                    insInY   (+ (cadr p1) offsetIn))

              (entmake
                (list
                  '(0 . "MTEXT")
                  '(100 . "AcDbEntity")
                  '(100 . "AcDbMText")
                  (cons 8 lay)
                  (list 10 insInX insInY 0.0)
                  (cons 40 th)
                  '(71 . 7) ;; Bottom Left attachment
                  (cons 1 (strcat "{\\fArial|b1;\\H1.4x;\\C4;" vpName "}\\P"
                                  "{\\fArial|b0;\\H0.85x;\\C8;SIZE: \\C2;" (rtos w 2 0) " \\U+00D7 " (rtos h 2 0) " mm}\\P"
                                  "{\\fArial|b0;\\H0.85x;\\C8;REF SCALE: \\C3;~1:" refScStr "}\\P"
                                  "{\\fArial|b0;\\H0.85x;\\C8;AREA: \\C3;" areaStr " m\\U+00B2   \\C8;|   \\C8;RATIO: \\C3;" ratioStr ":1}\\P"
                                  "{\\fArial|b0;\\H0.75x;\\C8;DATE: \\C9;" dtStr "}"))
                )
              )

              ;; 5. Outside Automatic Dimensions (Top & Right edges on R-ANNO-DIMS in Yellow)
              (setq dimLay (if *WF-LAYER-DIMS* *WF-LAYER-DIMS* "R-ANNO-DIMS"))
              (CadSetup:SetCurrentLayerSafe dimLay)

              ;; Apply Viewport-Scaled Yellow Dimension System Variables
              (setvar "DIMSCALE" sc)
              (setvar "DIMCLRD"  2)             ;; Yellow dimension line
              (setvar "DIMCLRE"  2)             ;; Yellow extension lines
              (setvar "DIMCLRT"  2)             ;; Yellow dimension text
              (setvar "DIMBLK"   "_ArchTick")   ;; Architectural tick
              (setvar "DIMASZ"   1.5)           ;; Scaled tick size
              (setvar "DIMTAD"   1)             ;; Text above line
              (setvar "DIMTXT"   2.5)           ;; 2.5 mm plotted text height (scaled by DIMSCALE)
              (setvar "DIMDEC"   0)             ;; Whole numbers (0 decimal places)
              (setvar "DIMZIN"   8)             ;; Suppress trailing zeros
              (if (tblsearch "style" "ARCH-TEXT")
                (setvar "DIMTXSTY" "ARCH-TEXT")
              )

              (setq dimOff (* sc 12.0))

              ;; Top Dimension (Width)
              (setq ptTop1   (list (car p1) (cadr p2) 0.0)
                    ptTop2   (list (car p2) (cadr p2) 0.0)
                    ptTopDim (list (* 0.5 (+ (car p1) (car p2))) (+ (cadr p2) dimOff) 0.0))
              (command "._dimaligned" "_non" ptTop1 "_non" ptTop2 "_non" ptTopDim)

              ;; Right Dimension (Height)
              (setq ptRt1   (list (car p2) (cadr p1) 0.0)
                    ptRt2   (list (car p2) (cadr p2) 0.0)
                    ptRtDim (list (+ (car p2) dimOff) (* 0.5 (+ (cadr p1) (cadr p2))) 0.0))
              (command "._dimaligned" "_non" ptRt1 "_non" ptRt2 "_non" ptRtDim)

              ;; Restore original dimension variables
              (if oldDimScale (setvar "DIMSCALE" oldDimScale))
              (if oldDimClrd  (setvar "DIMCLRD"  oldDimClrd))
              (if oldDimClre  (setvar "DIMCLRE"  oldDimClre))
              (if oldDimClrt  (setvar "DIMCLRT"  oldDimClrt))
              (if oldDimBlk
                (if (= oldDimBlk "") (setvar "DIMBLK" ".") (setvar "DIMBLK" oldDimBlk))
              )
              (if oldDimAsz   (setvar "DIMASZ"   oldDimAsz))
              (if oldDimTad   (setvar "DIMTAD"   oldDimTad))
              (if oldDimTxt   (setvar "DIMTXT"   oldDimTxt))
              (if oldDimDec   (setvar "DIMDEC"   oldDimDec))
              (if oldDimZin   (setvar "DIMZIN"   oldDimZin))
              (if oldDimTxSty (setvar "DIMTXSTY" oldDimTxSty))

              ;; Restore viewport layer for center guide point
              (CadSetup:SetCurrentLayerSafe lay)

              ;; 6. Drafting Center Guide Point using MidPoint helper
              (setq midPt (CadSetup:MidPoint p1 p2))
              (entmake
                (list
                  '(0 . "POINT")
                  (cons 8 lay)
                  (cons 10 midPt)
                )
              )
            )
          )
        )
      )
    )
  )

  ;; Final restoration
  (if oldDimScale (setvar "DIMSCALE" oldDimScale))
  (if oldDimClrd  (setvar "DIMCLRD"  oldDimClrd))
  (if oldDimClre  (setvar "DIMCLRE"  oldDimClre))
  (if oldDimClrt  (setvar "DIMCLRT"  oldDimClrt))
  (if oldDimBlk
    (if (= oldDimBlk "") (setvar "DIMBLK" ".") (setvar "DIMBLK" oldDimBlk))
  )
  (if oldDimAsz   (setvar "DIMASZ"   oldDimAsz))
  (if oldDimTad   (setvar "DIMTAD"   oldDimTad))
  (if oldDimTxt   (setvar "DIMTXT"   oldDimTxt))
  (if oldDimDec   (setvar "DIMDEC"   oldDimDec))
  (if oldDimZin   (setvar "DIMZIN"   oldDimZin))
  (if oldDimTxSty (setvar "DIMTXSTY" oldDimTxSty))

  (setvar "CLAYER" oldLayer)
  (if (boundp 'CadSetup:UndoEnd) (CadSetup:UndoEnd))
  (setvar "CMDECHO" oldEcho)

  (princ (strcat "\n[VP] Completed. Restored layer: " oldLayer))
  (princ)
    )
  )
)

(defun c:2 () (c:VP))


;;; --------------------------------------------------------------------------
;;; 3. STRUCTURAL & ARCHITECTURAL GRID SYSTEM GENERATOR (3 / GL)
;;; --------------------------------------------------------------------------

;; AutoLISP compatibility utilities (function bound predicate, symbol, string)
(if (not (boundp 'stringp))
  (defun stringp (val)
    (= (type val) 'STR)
  )
)

(if (not (boundp 'symbolp))
  (defun symbolp (sym)
    (= (type sym) 'SYM)
  )
)

(if (not (boundp 'fboundp))
  (defun fboundp (sym)
    (and (= (type sym) 'SYM)
         (boundp sym)
         (member (type (vl-symbol-value sym)) '(SUBR USUBR EXRXSUBR)))
  )
)

;; Global single-line and grid session attributes
(if (null *GL-SINGLE-TAG*)
  (setq *GL-SINGLE-TAG* "1")
)
(if (null *GL-BUBBLE-RAD*)
  (setq *GL-BUBBLE-RAD* 450.0)
)
(if (null *GL-GRID-EXT*)
  (setq *GL-GRID-EXT* 1000.0)
)
(if (null *GL-TEXT-HT*)
  (setq *GL-TEXT-HT* 300.0)
)
(if (null *GL-BUBBLE-POS*)
  (setq *GL-BUBBLE-POS* "End")
)

;; Helper: Parse spacing string into list of real bay distances
;; Handles: "4*6000", "6000, 5000, 7500", "3*6000, 4500, 2*3000"
(defun CadSetup:ParseGridSpacings (str / len i ch curToken tokens starPos count val res)
  (if (or (null str) (/= (type str) 'STR))
    nil
    (progn
      ;; Strip spaces around '*' (e.g. "4 * 6000" -> "4*6000")
      (while (vl-string-search " *" str)
        (setq str (vl-string-subst "*" " *" str))
      )
      (while (vl-string-search "* " str)
        (setq str (vl-string-subst "*" "* " str))
      )
      (setq len (strlen str)
            i 1
            curToken ""
            tokens nil)
      (while (<= i len)
        (setq ch (substr str i 1))
        (if (vl-position ch '(" " "," ";" "\t"))
          (progn
            (if (/= curToken "")
              (setq tokens (cons curToken tokens)
                    curToken ""))
          )
          (setq curToken (strcat curToken ch))
        )
        (setq i (1+ i))
      )
      (if (/= curToken "")
        (setq tokens (cons curToken tokens))
      )
      (setq tokens (reverse tokens))

      (setq res nil)
      (foreach tok tokens
        (setq starPos (vl-string-search "*" tok))
        (if starPos
          (progn
            (setq count (atoi (substr tok 1 starPos))
                  val   (distof (substr tok (+ starPos 2))))
            (if (and (> count 0) val (> val 0.0))
              (repeat count
                (setq res (cons (float val) res))
              )
            )
          )
          (progn
            (setq val (distof tok))
            (if (and val (> val 0.0))
              (setq res (cons (float val) res))
            )
          )
        )
      )
      (reverse res)
    )
  )
)

;; Helper: Auto-increment alpha strings ("A"->"B", "Z"->"AA", "AA"->"AB")
(defun CadSetup:IncrementAlpha (str / len lastChar rest)
  (setq len (strlen str))
  (if (<= len 0)
    "A"
    (progn
      (setq lastChar (ascii (strcase (substr str len 1)))
            rest     (substr str 1 (1- len)))
      (cond
        ((= lastChar 90) ;; 'Z'
         (if (= rest "")
           "AA"
           (strcat (CadSetup:IncrementAlpha rest) "A")
         ))
        ((and (>= lastChar 65) (< lastChar 90))
         (strcat rest (chr (1+ lastChar))))
        (t (strcat str "1"))
      )
    )
  )
)

;; Helper: Smart tag incrementer for numbers, letters, or compound tags ("1"->"2", "A"->"B", "GL-01"->"GL-02")
(defun CadSetup:IncrementGridTag (tag / len i prefix suffix nextNum nextNumStr)
  (if (or (null tag) (= tag ""))
    "1"
    (progn
      (setq len (strlen tag))
      (if (numberp (read tag))
        (itoa (1+ (atoi tag)))
        (progn
          (setq i len)
          (while (and (> i 0) (<= 48 (ascii (substr tag i 1)) 57))
            (setq i (1- i))
          )
          (if (< i len)
            (progn
              (setq prefix (substr tag 1 i)
                    suffix (substr tag (1+ i))
                    nextNum (1+ (atoi suffix))
                    nextNumStr (itoa nextNum))
              ;; Preserve zero-padding if any
              (while (< (strlen nextNumStr) (strlen suffix))
                (setq nextNumStr (strcat "0" nextNumStr))
              )
              (strcat prefix nextNumStr)
            )
            (CadSetup:IncrementAlpha tag)
          )
        )
      )
    )
  )
)

;; Helper: Interactive Sub-Menu Loop for Single Grid Line Attributes
(defun CadSetup:SingleGridSettingsPrompt ( / optVal inputVal loop )
  (princ (strcat "\n[GL Settings] Current: Placement=" *GL-BUBBLE-POS*
                 ", Radius=" (rtos *GL-BUBBLE-RAD* 2 1)
                 ", Extension=" (rtos *GL-GRID-EXT* 2 1)
                 ", TextHeight=" (rtos *GL-TEXT-HT* 2 1)))
  (setq loop T)
  (while loop
    (initget "Placement Radius Extension Text eXit P R E T X")
    (setq optVal (getkword "\nGrid Settings [Placement/Radius/Extension/Text/eXit] <eXit>: "))
    (cond
      ((or (= optVal "Placement") (= optVal "P"))
       (initget "End Start Both None E S B N")
       (setq inputVal (getkword (strcat "\nBubble Placement [End/Start/Both/None] <" *GL-BUBBLE-POS* ">: ")))
       (cond
         ((or (= inputVal "End") (= inputVal "E"))   (setq *GL-BUBBLE-POS* "End"))
         ((or (= inputVal "Start") (= inputVal "S")) (setq *GL-BUBBLE-POS* "Start"))
         ((or (= inputVal "Both") (= inputVal "B"))  (setq *GL-BUBBLE-POS* "Both"))
         ((or (= inputVal "None") (= inputVal "N"))  (setq *GL-BUBBLE-POS* "None"))
       )
       (princ (strcat "\n[GL Settings] Placement -> " *GL-BUBBLE-POS*))
      )
      ((or (= optVal "Radius") (= optVal "R"))
       (setq inputVal (getdist (strcat "\nBubble Radius <" (rtos *GL-BUBBLE-RAD* 2 1) ">: ")))
       (if (and inputVal (> inputVal 0.0))
         (setq *GL-BUBBLE-RAD* inputVal)
       )
       (princ (strcat "\n[GL Settings] Radius -> " (rtos *GL-BUBBLE-RAD* 2 1)))
      )
      ((or (= optVal "Extension") (= optVal "E"))
       (setq inputVal (getdist (strcat "\nLine Extension (Overshoot) <" (rtos *GL-GRID-EXT* 2 1) ">: ")))
       (if (and inputVal (> inputVal 0.0))
         (setq *GL-GRID-EXT* inputVal)
       )
       (princ (strcat "\n[GL Settings] Extension -> " (rtos *GL-GRID-EXT* 2 1)))
      )
      ((or (= optVal "Text") (= optVal "T"))
       (setq inputVal (getdist (strcat "\nText Height <" (rtos *GL-TEXT-HT* 2 1) ">: ")))
       (if (and inputVal (> inputVal 0.0))
         (setq *GL-TEXT-HT* inputVal)
       )
       (princ (strcat "\n[GL Settings] Text Height -> " (rtos *GL-TEXT-HT* 2 1)))
      )
      (t
       (setq loop nil)
      )
    )
  )
  (princ)
)

;; Helper: Draw Single Grid Line with Auto-Increment Bubble & Tags
(defun CadSetup:DrawSingleGridLine ( / *error* oldLayer oldEcho pt1 pt2 ang rad ext th pos
                                       lbl centerPt lineStart lineEnd mainLoop )
  (defun *error* (msg)
    (if oldEcho (setvar "CMDECHO" oldEcho))
    (if oldLayer (setvar "CLAYER" oldLayer))
    (if (boundp 'CadSetup:UndoReset) (CadSetup:UndoReset))
    (if (and msg (not (wcmatch (strcase msg t) "*break*,*cancel*,*exit*")))
      (princ (strcat "\n[GL-Single] Error: " msg))
    )
    (princ)
  )

  (setq oldEcho  (getvar "CMDECHO")
        oldLayer (getvar "CLAYER"))
  (setvar "CMDECHO" 0)

  ;; Ensure production layers are ready (thawed, turned ON, and unlocked)
  (if (boundp 'CadSetup:EnsureLayerReady)
    (progn
      (CadSetup:EnsureLayerReady "03-GRID-LINE")
      (CadSetup:EnsureLayerReady "R-ANNO-SYMB")
    )
    (if (boundp 'CadSetup:EnsureLayerFromDb)
      (progn
        (CadSetup:EnsureLayerFromDb "03-GRID-LINE")
        (CadSetup:EnsureLayerFromDb "R-ANNO-SYMB")
      )
    )
  )

  (princ "\n--- Single Grid Line Mode (Press Enter/Esc at prompt to finish) ---")
  (setq mainLoop T)
  (while mainLoop
    (initget 128 "Settings S")
    (setq pt1 (getpoint "\n[GL-Single] Specify Start Point or [Settings]: "))
    (cond
      ((or (eq pt1 "Settings") (eq pt1 "S"))
       (CadSetup:SingleGridSettingsPrompt)
      )
      ((listp pt1)
       (if (setq pt2 (getpoint pt1 "\n[GL-Single] Specify End Point: "))
         (progn
           (setq lbl (getstring t (strcat "\n[GL-Single] Enter Grid Bubble Label <" *GL-SINGLE-TAG* ">: ")))
           (if (or (null lbl) (= lbl ""))
             (setq lbl *GL-SINGLE-TAG*)
           )

           (CadSetup:UndoStart)

           (setq rad *GL-BUBBLE-RAD*
                 ext *GL-GRID-EXT*
                 th  *GL-TEXT-HT*
                 pos *GL-BUBBLE-POS*
                 ang (angle pt1 pt2))

           ;; Calculate line endpoints based on overshoot extension
           (setq lineStart (if (or (= pos "Start") (= pos "Both") (= pos "None"))
                             (polar pt1 (+ ang pi) ext)
                             pt1))
           (setq lineEnd   (if (or (= pos "End") (= pos "Both") (= pos "None"))
                             (polar pt2 ang ext)
                             pt2))

           ;; 1. Draw Grid Line on 03-GRID-LINE
           (entmake
             (list
               '(0 . "LINE")
               '(100 . "AcDbEntity")
               (cons 8 "03-GRID-LINE")
               '(100 . "AcDbLine")
               (cons 10 (trans lineStart 1 0))
               (cons 11 (trans lineEnd 1 0))
             )
           )

           ;; 2. Draw Start Bubble (if Start or Both)
           (if (or (= pos "Start") (= pos "Both"))
             (progn
               (setq centerPt (polar pt1 (+ ang pi) (+ ext rad)))
               (entmake
                 (list
                   '(0 . "CIRCLE")
                   '(100 . "AcDbEntity")
                   (cons 8 "R-ANNO-SYMB")
                   '(100 . "AcDbCircle")
                   (cons 10 (trans centerPt 1 0))
                   (cons 40 rad)
                 )
               )
               (entmake
                 (list
                   '(0 . "MTEXT")
                   '(100 . "AcDbEntity")
                   (cons 8 "R-ANNO-SYMB")
                   '(100 . "AcDbMText")
                   (cons 10 (trans centerPt 1 0))
                   (cons 40 th)
                   '(71 . 5)  ;; Middle Center
                   (cons 1 (strcat "{\\fArial|b1;" lbl "}"))
                 )
               )
             )
           )

           ;; 3. Draw End Bubble (if End or Both)
           (if (or (= pos "End") (= pos "Both"))
             (progn
               (setq centerPt (polar pt2 ang (+ ext rad)))
               (entmake
                 (list
                   '(0 . "CIRCLE")
                   '(100 . "AcDbEntity")
                   (cons 8 "R-ANNO-SYMB")
                   '(100 . "AcDbCircle")
                   (cons 10 (trans centerPt 1 0))
                   (cons 40 rad)
                 )
               )
               (entmake
                 (list
                   '(0 . "MTEXT")
                   '(100 . "AcDbEntity")
                   (cons 8 "R-ANNO-SYMB")
                   '(100 . "AcDbMText")
                   (cons 10 (trans centerPt 1 0))
                   (cons 40 th)
                   '(71 . 5)  ;; Middle Center
                   (cons 1 (strcat "{\\fArial|b1;" lbl "}"))
                 )
               )
             )
           )

           (CadSetup:UndoEnd)

           ;; Increment tag for next line
           (setq *GL-SINGLE-TAG* (CadSetup:IncrementGridTag lbl))
           (princ (strcat "\n[GL-Single] Placed line '" lbl "'. Next default tag: '" *GL-SINGLE-TAG* "'."))
         )
         (setq mainLoop nil)
       )
      )
      (t
       (setq mainLoop nil)
      )
    )
  )

  (setvar "CLAYER" oldLayer)
  (setvar "CMDECHO" oldEcho)
  (princ (strcat "\n[GL-Single] Completed. Restored layer: " oldLayer))
  (princ)
)

;; Helper: Draw Full Grid System with Bubbles and Dimensions
(defun CadSetup:DrawGridSystem ( xSpacings xStartTag ySpacings yStartTag
                                 bubblePos bubbleRad gridExt textHt
                                 addBayDims addTotalDims dimOffset /
                                 *error* oldLayer oldEcho insPt rotAngle cosA sinA
                                 cumX curX cumY curY xTot yTot
                                 _toWorld i curTag xVal yVal
                                 pStart pEnd pCircle
                                 hasTopBubble hasBottomBubble hasLeftBubble hasRightBubble
                                 yBayDim yTotDim xBayDim xTotDim p1 p2 pDim )

  (defun *error* (msg)
    (if oldEcho (setvar "CMDECHO" oldEcho))
    (if oldLayer (setvar "CLAYER" oldLayer))
    (if (boundp 'CadSetup:UndoReset) (CadSetup:UndoReset))
    (if (and msg (not (wcmatch (strcase msg t) "*break*,*cancel*,*exit*")))
      (princ (strcat "\n[GL-Grid Error]: " msg))
    )
    (princ)
  )

  (setq oldEcho  (getvar "CMDECHO")
        oldLayer (getvar "CLAYER"))
  (setvar "CMDECHO" 0)

  ;; 1. Prompt for Insertion Point and Rotation
  (setq insPt (getpoint "\n[GL] Specify Grid System Origin Point (Intersection 1-A): "))
  (if (null insPt)
    (progn
      (princ "\n[GL] Grid insertion cancelled.")
      (setvar "CLAYER" oldLayer)
      (setvar "CMDECHO" oldEcho)
      (exit)
    )
  )

  (setq rotAngle (getangle insPt "\n[GL] Specify Grid Rotation Angle <0.0>: "))
  (if (null rotAngle) (setq rotAngle 0.0))

  ;; Ensure production layers are ready (thawed, turned ON, and unlocked)
  (if (boundp 'CadSetup:EnsureLayerReady)
    (progn
      (CadSetup:EnsureLayerReady "03-GRID-LINE")
      (CadSetup:EnsureLayerReady "R-ANNO-SYMB")
      (CadSetup:EnsureLayerReady "R-ANNO-DIMS")
    )
    (if (boundp 'CadSetup:EnsureLayerFromDb)
      (progn
        (CadSetup:EnsureLayerFromDb "03-GRID-LINE")
        (CadSetup:EnsureLayerFromDb "R-ANNO-SYMB")
        (CadSetup:EnsureLayerFromDb "R-ANNO-DIMS")
      )
    )
  )

  (CadSetup:UndoStart)

  ;; 2. Coordinate Transformation Math
  (setq cosA (cos rotAngle)
        sinA (sin rotAngle))

  (defun _toWorld (lx ly)
    (list
      (+ (car insPt)  (- (* lx cosA) (* ly sinA)))
      (+ (cadr insPt) (+ (* lx sinA) (* ly cosA)))
      (if (caddr insPt) (caddr insPt) 0.0)
    )
  )

  ;; 3. Compute Cumulative Coordinate Lists
  ;; X coordinates (vertical lines at each x)
  (setq cumX (list 0.0)
        curX 0.0)
  (foreach sp xSpacings
    (setq curX (+ curX sp)
          cumX (cons curX cumX))
  )
  (setq cumX (reverse cumX))
  (setq xTot (last cumX))

  ;; Y coordinates (horizontal lines at each y)
  (setq cumY (list 0.0)
        curY 0.0)
  (foreach sp ySpacings
    (setq curY (+ curY sp)
          cumY (cons curY cumY))
  )
  (setq cumY (reverse cumY))
  (setq yTot (last cumY))

  ;; Determine bubble flags:
  ;; 0 = Both Ends, 1 = Top & Left Only, 2 = Bottom & Right Only, 3 = None
  (setq hasTopBubble    (or (= bubblePos 0) (= bubblePos 1))
        hasBottomBubble (or (= bubblePos 0) (= bubblePos 2))
        hasLeftBubble   (or (= bubblePos 0) (= bubblePos 1))
        hasRightBubble  (or (= bubblePos 0) (= bubblePos 2)))

  ;; 4. Draw Vertical Grid Lines (X-Axis)
  (setq curTag xStartTag
        i 0)
  (while (< i (length cumX))
    (setq xVal (nth i cumX))

    ;; Grid Line (03-GRID-LINE)
    (setq pStart (_toWorld xVal (- 0.0 gridExt))
          pEnd   (_toWorld xVal (+ yTot gridExt)))
    (entmake
      (list
        '(0 . "LINE")
        '(100 . "AcDbEntity")
        (cons 8 "03-GRID-LINE")
        '(100 . "AcDbLine")
        (cons 10 (trans pStart 1 0))
        (cons 11 (trans pEnd 1 0))
      )
    )

    ;; Top Bubble
    (if hasTopBubble
      (progn
        (setq pCircle (_toWorld xVal (+ yTot gridExt bubbleRad)))
        (entmake
          (list
            '(0 . "CIRCLE")
            '(100 . "AcDbEntity")
            (cons 8 "R-ANNO-SYMB")
            '(100 . "AcDbCircle")
            (cons 10 (trans pCircle 1 0))
            (cons 40 bubbleRad)
          )
        )
        (entmake
          (list
            '(0 . "MTEXT")
            '(100 . "AcDbEntity")
            (cons 8 "R-ANNO-SYMB")
            '(100 . "AcDbMText")
            (cons 10 (trans pCircle 1 0))
            (cons 40 textHt)
            '(71 . 5) ;; Middle Center
            (cons 1 (strcat "{\\fArial|b1;" curTag "}"))
          )
        )
      )
    )

    ;; Bottom Bubble
    (if hasBottomBubble
      (progn
        (setq pCircle (_toWorld xVal (- 0.0 gridExt bubbleRad)))
        (entmake
          (list
            '(0 . "CIRCLE")
            '(100 . "AcDbEntity")
            (cons 8 "R-ANNO-SYMB")
            '(100 . "AcDbCircle")
            (cons 10 (trans pCircle 1 0))
            (cons 40 bubbleRad)
          )
        )
        (entmake
          (list
            '(0 . "MTEXT")
            '(100 . "AcDbEntity")
            (cons 8 "R-ANNO-SYMB")
            '(100 . "AcDbMText")
            (cons 10 (trans pCircle 1 0))
            (cons 40 textHt)
            '(71 . 5) ;; Middle Center
            (cons 1 (strcat "{\\fArial|b1;" curTag "}"))
          )
        )
      )
    )

    (setq curTag (CadSetup:IncrementGridTag curTag)
          i (1+ i))
  )

  ;; 5. Draw Horizontal Grid Lines (Y-Axis)
  (setq curTag yStartTag
        i 0)
  (while (< i (length cumY))
    (setq yVal (nth i cumY))

    ;; Grid Line (03-GRID-LINE)
    (setq pStart (_toWorld (- 0.0 gridExt) yVal)
          pEnd   (_toWorld (+ xTot gridExt) yVal))
    (entmake
      (list
        '(0 . "LINE")
        '(100 . "AcDbEntity")
        (cons 8 "03-GRID-LINE")
        '(100 . "AcDbLine")
        (cons 10 (trans pStart 1 0))
        (cons 11 (trans pEnd 1 0))
      )
    )

    ;; Left Bubble
    (if hasLeftBubble
      (progn
        (setq pCircle (_toWorld (- 0.0 gridExt bubbleRad) yVal))
        (entmake
          (list
            '(0 . "CIRCLE")
            '(100 . "AcDbEntity")
            (cons 8 "R-ANNO-SYMB")
            '(100 . "AcDbCircle")
            (cons 10 (trans pCircle 1 0))
            (cons 40 bubbleRad)
          )
        )
        (entmake
          (list
            '(0 . "MTEXT")
            '(100 . "AcDbEntity")
            (cons 8 "R-ANNO-SYMB")
            '(100 . "AcDbMText")
            (cons 10 (trans pCircle 1 0))
            (cons 40 textHt)
            '(71 . 5) ;; Middle Center
            (cons 1 (strcat "{\\fArial|b1;" curTag "}"))
          )
        )
      )
    )

    ;; Right Bubble
    (if hasRightBubble
      (progn
        (setq pCircle (_toWorld (+ xTot gridExt bubbleRad) yVal))
        (entmake
          (list
            '(0 . "CIRCLE")
            '(100 . "AcDbEntity")
            (cons 8 "R-ANNO-SYMB")
            '(100 . "AcDbCircle")
            (cons 10 (trans pCircle 1 0))
            (cons 40 bubbleRad)
          )
        )
        (entmake
          (list
            '(0 . "MTEXT")
            '(100 . "AcDbEntity")
            (cons 8 "R-ANNO-SYMB")
            '(100 . "AcDbMText")
            (cons 10 (trans pCircle 1 0))
            (cons 40 textHt)
            '(71 . 5) ;; Middle Center
            (cons 1 (strcat "{\\fArial|b1;" curTag "}"))
          )
        )
      )
    )

    (setq curTag (CadSetup:IncrementGridTag curTag)
          i (1+ i))
  )

  ;; 6. Generate Automated Dimensions (R-ANNO-DIMS)
  (if (or (= addBayDims 1) (= addTotalDims 1))
    (progn
      (if (boundp 'CadSetup:SetCurrentLayerSafe)
        (CadSetup:SetCurrentLayerSafe "R-ANNO-DIMS")
        (setvar "CLAYER" "R-ANNO-DIMS")
      )

      ;; X-Axis Dimension Placements (Above Top)
      (setq yBayDim (+ yTot gridExt (if hasTopBubble (* 2.0 bubbleRad) 0.0) dimOffset))
      (setq yTotDim (+ yBayDim (if (= addBayDims 1) dimOffset 0.0)))

      ;; Bay Dimensions along X
      (if (= addBayDims 1)
        (progn
          (setq i 0)
          (while (< i (1- (length cumX)))
            (setq p1   (_toWorld (nth i cumX) yTot)
                  p2   (_toWorld (nth (1+ i) cumX) yTot)
                  pDim (_toWorld (* 0.5 (+ (nth i cumX) (nth (1+ i) cumX))) yBayDim))
            (command "._dimaligned" "_non" p1 "_non" p2 "_non" pDim)
            (setq i (1+ i))
          )
        )
      )

      ;; Total / Overall Dimension along X
      (if (= addTotalDims 1)
        (progn
          (setq p1   (_toWorld 0.0 yTot)
                p2   (_toWorld xTot yTot)
                pDim (_toWorld (* 0.5 xTot) yTotDim))
          (command "._dimaligned" "_non" p1 "_non" p2 "_non" pDim)
        )
      )

      ;; Y-Axis Dimension Placements (To Left)
      (setq xBayDim (- 0.0 (+ gridExt (if hasLeftBubble (* 2.0 bubbleRad) 0.0) dimOffset)))
      (setq xTotDim (- xBayDim (if (= addBayDims 1) dimOffset 0.0)))

      ;; Bay Dimensions along Y
      (if (= addBayDims 1)
        (progn
          (setq i 0)
          (while (< i (1- (length cumY)))
            (setq p1   (_toWorld 0.0 (nth i cumY))
                  p2   (_toWorld 0.0 (nth (1+ i) cumY))
                  pDim (_toWorld xBayDim (* 0.5 (+ (nth i cumY) (nth (1+ i) cumY)))))
            (command "._dimaligned" "_non" p1 "_non" p2 "_non" pDim)
            (setq i (1+ i))
          )
        )
      )

      ;; Total / Overall Dimension along Y
      (if (= addTotalDims 1)
        (progn
          (setq p1   (_toWorld 0.0 0.0)
                p2   (_toWorld 0.0 yTot)
                pDim (_toWorld xTotDim (* 0.5 yTot)))
          (command "._dimaligned" "_non" p1 "_non" p2 "_non" pDim)
        )
      )
    )
  )

  (CadSetup:UndoEnd)

  (setvar "CLAYER" oldLayer)
  (setvar "CMDECHO" oldEcho)
  (princ (strcat "\n[GL] Grid System placed successfully (" 
                 (itoa (length cumX)) "x" (itoa (length cumY)) " lines). Restored layer: " oldLayer))
  (princ)
)

;; Dialog Controller: c:GRID-GENERATOR-DIALOG
(defun c:GRID-GENERATOR-DIALOG ( / *error* dclPath dclId act
                                   strX strXTag strY strYTag
                                   popBubble bubbleRad gridExt textHt
                                   bayDims totalDims dimOff
                                   xList yList )

  (defun *error* (msg)
    (if (and dclId (>= dclId 0))
      (vl-catch-all-apply 'unload_dialog (list dclId))
    )
    (if (and msg (not (wcmatch (strcase msg t) "*cancel*,*exit*,*quit*")))
      (princ (strcat "\n[GL Error]: " msg))
    )
    (princ)
  )

  ;; Robust DCL search
  (setq dclPath nil)
  (cond
    ((and (boundp 'CadSetup:GetDir) CadSetup:GetDir (setq dclPath (strcat (CadSetup:GetDir) "\\UI\\GRID-GENERATOR.dcl")) (findfile dclPath))
     dclPath)
    ((setq dclPath (findfile "GRID-GENERATOR.dcl"))
     dclPath)
    ((setq dclPath (findfile "UI\\GRID-GENERATOR.dcl"))
     dclPath)
    ((setq dclPath (findfile "d:\\Cad-Setup\\Cad-Setup-v4\\UI\\GRID-GENERATOR.dcl"))
     dclPath)
  )

  (if (or (null dclPath) (not (findfile dclPath)))
    (progn
      (princ "\n[GL Error]: GRID-GENERATOR.dcl not found in UI/ directory.")
      (exit)
    )
  )

  (setq dclId (load_dialog dclPath))
  (if (or (null dclId) (< dclId 0))
    (progn
      (princ (strcat "\n[GL Error]: Failed to load dialog file " dclPath))
      (exit)
    )
  )

  (if (not (new_dialog "grid_system_dialog" dclId))
    (progn
      (unload_dialog dclId)
      (princ "\n[GL Error]: Dialog definition 'grid_system_dialog' not found in DCL.")
      (exit)
    )
  )

  ;; Initialize Pop-up list for bubble positions
  (start_list "pop_bubble_pos")
  (mapcar 'add_list '("0. Both Ends (Top/Bottom & Left/Right)"
                      "1. Top & Left Only"
                      "2. Bottom & Right Only"
                      "3. None (Lines Only)"))
  (end_list)

  ;; Fixed Sensible Defaults
  (set_tile "eb_x_spacings" "4*6000")
  (set_tile "eb_x_tag"      "1")
  (set_tile "eb_y_spacings" "3*5000")
  (set_tile "eb_y_tag"      "A")
  (set_tile "pop_bubble_pos"
    (cond
      ((= *GL-BUBBLE-POS* "Both")  "0")
      ((= *GL-BUBBLE-POS* "Start") "1")
      ((= *GL-BUBBLE-POS* "End")   "2")
      ((= *GL-BUBBLE-POS* "None")  "3")
      (t "0")
    )
  )
  (set_tile "eb_bubble_rad"  (rtos *GL-BUBBLE-RAD* 2 1))
  (set_tile "eb_grid_ext"    (rtos *GL-GRID-EXT* 2 1))
  (set_tile "eb_text_height" (rtos *GL-TEXT-HT* 2 1))
  (set_tile "tog_bay_dims"   "1")
  (set_tile "tog_total_dims" "1")
  (set_tile "eb_dim_offset"  "1200")

  ;; Button Handlers
  (action_tile "btn_single" "(done_dialog 2)")
  (action_tile "cancel"     "(done_dialog 0)")
  (action_tile "accept"
    "(progn
       (setq strX       (get_tile \"eb_x_spacings\")
             strXTag    (get_tile \"eb_x_tag\")
             strY       (get_tile \"eb_y_spacings\")
             strYTag    (get_tile \"eb_y_tag\")
             popBubble  (atoi (get_tile \"pop_bubble_pos\"))
             bubbleRad  (distof (get_tile \"eb_bubble_rad\"))
             gridExt    (distof (get_tile \"eb_grid_ext\"))
             textHt     (distof (get_tile \"eb_text_height\"))
             bayDims    (atoi (get_tile \"tog_bay_dims\"))
             totalDims  (atoi (get_tile \"tog_total_dims\"))
             dimOff     (distof (get_tile \"eb_dim_offset\")))
       (done_dialog 1)
     )"
  )

  (setq act (start_dialog))
  (unload_dialog dclId)

  ;; Dispatch user action
  (cond
    ((= act 1)
     ;; Validate and process inputs
     (setq xList (CadSetup:ParseGridSpacings strX))
     (setq yList (CadSetup:ParseGridSpacings strY))

     (if (or (null xList) (null yList))
       (princ "\n[GL Error]: Invalid bay spacing syntax. Example: 4*6000 or 6000,5000,7500")
       (progn
         (if (and bubbleRad (> bubbleRad 0.0)) (setq *GL-BUBBLE-RAD* bubbleRad))
         (if (and gridExt   (> gridExt 0.0))   (setq *GL-GRID-EXT* gridExt))
         (if (and textHt    (> textHt 0.0))    (setq *GL-TEXT-HT* textHt))
         (setq *GL-BUBBLE-POS*
           (cond
             ((= popBubble 0) "Both")
             ((= popBubble 1) "Start")
             ((= popBubble 2) "End")
             ((= popBubble 3) "None")
             (t "Both")
           )
         )

         (CadSetup:DrawGridSystem xList strXTag yList strYTag
                                  popBubble *GL-BUBBLE-RAD* *GL-GRID-EXT* *GL-TEXT-HT*
                                  bayDims totalDims dimOff)
       )
     )
    )
    ((= act 2)
     ;; Jump directly into Single Line Mode
     (CadSetup:DrawSingleGridLine)
    )
    (t
     (princ "\n[GL] Cancelled.")
    )
  )
  (princ)
)

;; Main Command Entry Point: GL / 3
(defun c:GL ( / ss lay opt )
  (setq ss (ssget "_I"))
  (setq lay (if *WF-LAYER-GL* *WF-LAYER-GL* "03-GRID-LINE"))

  (if (and ss (> (sslength ss) 0))
    (progn
      (CadSetup:AssignEntitiesToLayer ss lay)
      (princ)
    )
    (progn
      (initget "Dialog Single Line GL 3")
      (setq opt (getkword "\nGrid System [Dialog/Single Line] <Dialog>: "))
      (cond
        ((or (null opt) (= opt "Dialog") (= opt "D"))
         (c:GRID-GENERATOR-DIALOG)
        )
        ((or (= opt "Single") (= opt "Line") (= opt "GL") (= opt "3"))
         (CadSetup:DrawSingleGridLine)
        )
        (t
         (c:GRID-GENERATOR-DIALOG)
        )
      )
      (princ)
    )
  )
)

(defun c:3 () (c:GL))

;; Direct command shortcuts for Single Grid Line placement
(defun c:GLS () (CadSetup:DrawSingleGridLine) (princ))
(defun c:GL1 () (CadSetup:DrawSingleGridLine) (princ))


;;; --------------------------------------------------------------------------
;;; SHARED UTILITIES FOR DIALOG SELECTORS (LL & ML)
;;; --------------------------------------------------------------------------

;; Snapshot master layers data on first load for 'Reset to DB Defaults' feature
(if (and (boundp '*CadSetup-Layers-Data*) (null (boundp '*CadSetup-Master-Layers-Backup*)))
  (setq *CadSetup-Master-Layers-Backup* *CadSetup-Layers-Data*)
)

;; CadSetup:GetLoadedLinetypes - Returns sorted list of all linetypes currently loaded in the drawing
(defun CadSetup:GetLoadedLinetypes ( / ltEntry ltList )
  (setq ltList nil)
  (setq ltEntry (tblnext "LTYPE" t))
  (while ltEntry
    (setq ltList (cons (cdr (assoc 2 ltEntry)) ltList))
    (setq ltEntry (tblnext "LTYPE" nil))
  )
  (if ltList (acad_strlsort ltList) '("Continuous"))
)

;; CadSetup:SanitizeText - Replaces unicode dashes or common ANSI corruptions with clean ASCII
(defun CadSetup:SanitizeText (str / res)
  (if (or (null str) (= str ""))
    ""
    (progn
      (setq res str)
      (while (vl-string-search "—" res) (setq res (vl-string-subst " - " "—" res)))
      (while (vl-string-search "–" res) (setq res (vl-string-subst " - " "–" res)))
      (while (vl-string-search "â€“" res) (setq res (vl-string-subst " - " "â€“" res)))
      (while (vl-string-search "â€”" res) (setq res (vl-string-subst " - " "â€”" res)))
      (while (vl-string-search "Â°" res) (setq res (vl-string-subst " deg" "Â°" res)))
      (while (vl-string-search "°" res) (setq res (vl-string-subst " deg" "°" res)))
      res
    )
  )
)

;; CadSetup:WrapText3Lines - Breaks a string into up to 3 lines at word boundaries (~50 chars)
(defun CadSetup:WrapText3Lines (str maxLen / words curLine lineList pos w)
  (setq str (CadSetup:SanitizeText str))
  (if (or (null str) (= str ""))
    '("-" " " " ")
    (progn
      (setq words nil)
      (while (and str (/= str ""))
        (setq pos (vl-string-search " " str))
        (if pos
          (progn
            (setq w (substr str 1 pos))
            (if (> (strlen w) 0) (setq words (cons w words)))
            (setq str (substr str (+ pos 2)))
          )
          (progn
            (if (> (strlen str) 0) (setq words (cons str words)))
            (setq str nil)
          )
        )
      )
      (setq words (reverse words))
      (setq lineList nil
            curLine  "")
      (foreach w words
        (if (= curLine "")
          (setq curLine w)
          (if (<= (+ (strlen curLine) 1 (strlen w)) maxLen)
            (setq curLine (strcat curLine " " w))
            (progn
              (setq lineList (cons curLine lineList))
              (setq curLine w)
            )
          )
        )
      )
      (if (/= curLine "") (setq lineList (cons curLine lineList)))
      (setq lineList (reverse lineList))
      (list
        (if (>= (length lineList) 1) (nth 0 lineList) "-")
        (if (>= (length lineList) 2) (nth 1 lineList) " ")
        (if (>= (length lineList) 3) (nth 2 lineList) " ")
      )
    )
  )
)

;; CadSetup:UpdateLayerDataInMemory - Modifies hatch/transparency specs in *CadSetup-Layers-Data*
(defun CadSetup:UpdateLayerDataInMemory (lName newPat newScl newRot newTrans / oldRow newRow)
  (if (boundp '*CadSetup-Layers-Data*)
    (progn
      (setq oldRow (assoc (strcase lName) *CadSetup-Layers-Data*))
      (if oldRow
        (progn
          (setq newRow (list
            (nth 0 oldRow)
            (nth 1 oldRow)
            (nth 2 oldRow)
            (nth 3 oldRow)
            (nth 4 oldRow)
            (nth 5 oldRow)
            (if newPat newPat (nth 6 oldRow))
            (if (numberp newScl) newScl (nth 7 oldRow))
            (if (numberp newRot) newRot (nth 8 oldRow))
            (if (numberp newTrans) newTrans (nth 9 oldRow))
            (nth 10 oldRow)
            (nth 11 oldRow)
          ))
          (setq *CadSetup-Layers-Data*
            (mapcar
              (function (lambda (r) (if (= (strcase (car r)) (strcase lName)) newRow r)))
              *CadSetup-Layers-Data*
            )
          )
        )
      )
    )
  )
)


;;; --------------------------------------------------------------------------
;;; 4. UNIFIED DYNAMIC LAYER SELECTOR (UDLS) & DRAWING WORKFLOWS (4 / 5 / -)
;;; --------------------------------------------------------------------------

;; Global session flag for Key 5 Smart Auto-Hatch
(if (not (boundp '*CadSetup-AutoHatch-Enabled*))
  (setq *CadSetup-AutoHatch-Enabled* T)
)

;; CadSetup:GetDrawingLayersByPattern - Returns sorted list of active drawing layers matching pattern
(defun CadSetup:GetDrawingLayersByPattern (pat / layEntry layList)
  (setq layList nil)
  (setq layEntry (tblnext "LAYER" t))
  (while layEntry
    (if (wcmatch (strcase (cdr (assoc 2 layEntry))) (strcase pat))
      (setq layList (cons (cdr (assoc 2 layEntry)) layList))
    )
    (setq layEntry (tblnext "LAYER" nil))
  )
  (if layList
    (acad_strlsort layList)
    nil
  )
)

;; Legacy wrappers for backward compatibility
(defun CadSetup:GetDrawingLineLayers ()
  (CadSetup:GetDrawingLayersByPattern "R-LINE-*")
)

(defun CadSetup:GetDrawingMaterialLayers ()
  (CadSetup:GetDrawingLayersByPattern "R-MAT-*")
)

(defun CadSetup:GetDrawingRLayers ()
  (CadSetup:GetDrawingLayersByPattern "R-*")
)

;; CadSetup:EnsureLineLayersLoaded - Ensures standard line layers from Db_Layers.lsp if missing
(defun CadSetup:EnsureLineLayersLoaded ( / allData count row lName )
  (setq allData (if (boundp '*CadSetup-Layers-Data*) *CadSetup-Layers-Data* nil)
        count 0)
  (if allData
    (foreach row allData
      (setq lName (if (nth 0 row) (vl-princ-to-string (nth 0 row)) ""))
      (if (wcmatch (strcase lName) "R-LINE-*")
        (if (CadSetup:EnsureLayerFromDb lName)
          (setq count (1+ count))
        )
      )
    )
  )
  count
)

;; CadSetup:EnsureMaterialLayersLoaded - Ensures standard material layers from Db_Layers.lsp if missing
(defun CadSetup:EnsureMaterialLayersLoaded ( / allData count row lName )
  (setq allData (if (boundp '*CadSetup-Layers-Data*) *CadSetup-Layers-Data* nil)
        count 0)
  (if allData
    (foreach row allData
      (setq lName (if (nth 0 row) (vl-princ-to-string (nth 0 row)) ""))
      (if (wcmatch (strcase lName) "R-MAT-*")
        (if (CadSetup:EnsureLayerFromDb lName)
          (setq count (1+ count))
        )
      )
    )
  )
  count
)

;; CadSetup:EnsureAnnotationLayersLoaded - Ensures standard annotation layers from Db_Layers.lsp if missing
(defun CadSetup:EnsureAnnotationLayersLoaded ( / allData count row lName )
  (setq allData (if (boundp '*CadSetup-Layers-Data*) *CadSetup-Layers-Data* nil)
        count 0)
  (if allData
    (foreach row allData
      (setq lName (if (nth 0 row) (vl-princ-to-string (nth 0 row)) ""))
      (if (wcmatch (strcase lName) "R-ANNO-*")
        (if (CadSetup:EnsureLayerFromDb lName)
          (setq count (1+ count))
        )
      )
    )
  )
  count
)

;; CadSetup:EnsureHardwareLayersLoaded - Ensures standard hardware layers from Db_Layers.lsp if missing
(defun CadSetup:EnsureHardwareLayersLoaded ( / allData count row lName )
  (setq allData (if (boundp '*CadSetup-Layers-Data*) *CadSetup-Layers-Data* nil)
        count 0)
  (if allData
    (foreach row allData
      (setq lName (if (nth 0 row) (vl-princ-to-string (nth 0 row)) ""))
      (if (wcmatch (strcase lName) "R-HARD-*")
        (if (CadSetup:EnsureLayerFromDb lName)
          (setq count (1+ count))
        )
      )
    )
  )
  count
)

;; CadSetup:DrawPolyline - Sets current layer and launches native Polyline command with atomic undo
(defun CadSetup:DrawPolyline (layName / *error* oldEcho)
  (defun *error* (msg)
    (if oldEcho (setvar "CMDECHO" oldEcho))
    (if (boundp 'CadSetup:UndoReset) (CadSetup:UndoReset))
    (if (and msg (not (wcmatch (strcase msg t) "*break*,*cancel*,*exit*")))
      (princ (strcat "\n[PL] Error: " msg))
    )
    (princ)
  )

  (setq oldEcho (getvar "CMDECHO"))
  (if (boundp 'CadSetup:UndoStart) (CadSetup:UndoStart))
  (CadSetup:SetCurrentLayerSafe layName)
  (setq *WF-LAYER-LL* layName
        *WF-LAYER-RL* layName)
  (princ (strcat "\n[PL] Current layer set to: " layName))
  (setvar "CMDECHO" 1)
  (initcommandversion)
  (command "_.PLINE")
  (while (> (getvar "CMDACTIVE") 0)
    (command pause)
  )
  (if (boundp 'CadSetup:UndoEnd) (CadSetup:UndoEnd))
  (setvar "CMDECHO" oldEcho)
  (princ)
)

;; CadSetup:DrawRectangle - Draws rectangle on specified layer using latest default Rectangle command with Dynamic Input and Smart Auto-Hatch
(defun CadSetup:DrawRectangle (layName / *error* oldEcho lastEnt rectEnt rectObj dbRow hPat hScl hRot hTrans hTargetLay hObj)
  (defun *error* (msg)
    (if (boundp 'CadSetup:UndoReset) (CadSetup:UndoReset))
    (if oldEcho (setvar "CMDECHO" oldEcho))
    (if (and msg (not (wcmatch (strcase msg t) "*break*,*cancel*,*exit*")))
      (princ (strcat "\n[REC] Error: " msg))
    )
    (princ)
  )

  (setq oldEcho (getvar "CMDECHO"))
  (setvar "CMDECHO" 0)
  (CadSetup:SetCurrentLayerSafe layName)
  (setq *WF-LAYER-ML* layName
        *WF-LAYER-RL* layName)
  (princ (strcat "\n[REC] Current layer set to: " layName))

  ;; Lookup layer's preset hatching specifications from active in-memory DB
  (setq dbRow (if (boundp 'CadSetup:GetLayerData) (CadSetup:GetLayerData layName) nil))
  (if (null dbRow)
    (setq dbRow (assoc (strcase layName) (if (boundp '*CadSetup-Layers-Data*) *CadSetup-Layers-Data* nil)))
  )
  (if dbRow
    (setq hPat   (if (nth 6 dbRow) (vl-princ-to-string (nth 6 dbRow)) "NONE")
          hScl   (if (numberp (nth 7 dbRow)) (nth 7 dbRow) 1.0)
          hRot   (if (numberp (nth 8 dbRow)) (nth 8 dbRow) 0.0)
          hTrans (if (numberp (nth 9 dbRow)) (nth 9 dbRow) 0))
    (setq hPat "NONE" hScl 1.0 hRot 0.0 hTrans 0)
  )

  ;; Target hatch layer: dedicated R-HTCH-GENR or system HPLAYER
  (setq hTargetLay (if (and (boundp '*DEFAULT-HPLAYER*) *DEFAULT-HPLAYER* (/= *DEFAULT-HPLAYER* ""))
                     *DEFAULT-HPLAYER*
                     "R-HTCH-GENR"))
  (if (and *CadSetup-AutoHatch-Enabled* (boundp 'CadSetup:EnsureLayerReady))
    (CadSetup:EnsureLayerReady hTargetLay)
  )

  (if (and *CadSetup-AutoHatch-Enabled* hPat (/= (strcase hPat) "NONE") (/= hPat ""))
    (princ (strcat "\n[REC Smart Auto-Hatch: ON] Pattern: " hPat " | Scale: " (rtos hScl 2 2) " | Rot: " (rtos hRot 2 1) " deg | Target: " hTargetLay))
    (princ "\n[REC Smart Auto-Hatch: OFF or Pattern is NONE]")
  )

  (if (boundp 'CadSetup:UndoStart) (CadSetup:UndoStart))
  (setq lastEnt (entlast))
  (setvar "CMDECHO" 1)
  (initcommandversion)
  (command "_.RECTANG")
  (while (> (getvar "CMDACTIVE") 0)
    (command pause)
  )
  (setvar "CMDECHO" 0)

  (setq rectEnt (entlast))
  (if (and rectEnt (not (eq rectEnt lastEnt)))
    (progn
      (if (and *CadSetup-AutoHatch-Enabled*
               hPat
               (/= (strcase hPat) "NONE")
               (/= hPat ""))
        (progn
          (setq rectObj (vlax-ename->vla-object rectEnt))
          (if rectObj
            (progn
              ;; Generate associative hatch on dedicated hatch layer
              (setq hObj (CadSetup:CreateHatch rectObj hPat hScl hRot nil hTargetLay))
              (if hObj
                (progn
                  ;; Apply material transparency if specified (> 0)
                  (if (and (numberp hTrans) (> hTrans 0))
                    (CadSetup:SetEntityTransparency hObj hTrans)
                  )
                  (princ (strcat "\n[Auto-Hatch] Filled boundary with " hPat " (Scale " (rtos hScl 2 2) ") on " hTargetLay "."))
                )
                (princ (strcat "\n[Auto-Hatch Warning] Failed to generate hatch pattern '" hPat "'."))
              )
            )
          )
        )
        (if (and *CadSetup-AutoHatch-Enabled* (or (null hPat) (= (strcase hPat) "NONE") (= hPat "")))
          (princ "\n[REC] Rectangle created. (Hatch skipped: Pattern set to NONE).")
        )
      )
    )
  )
  (if (boundp 'CadSetup:UndoEnd) (CadSetup:UndoEnd))
  (setvar "CMDECHO" oldEcho)
  (princ (strcat "\n[REC] Active layer remains: " layName))
  (princ)
)

;; CadSetup:DrawContinuousRectangles - Backward compatibility alias to CadSetup:DrawRectangle
(defun CadSetup:DrawContinuousRectangles (layName)
  (CadSetup:DrawRectangle layName)
)

;; CadSetup:DrawRLayerPolyline & CadSetup:DrawRLayerRectangles - Compatibility aliases
(defun CadSetup:DrawRLayerPolyline (layName)
  (CadSetup:DrawPolyline layName)
)

(defun CadSetup:DrawRLayerRectangles (layName)
  (CadSetup:DrawRectangle layName)
)

;; =============================================================================
;; CadSetup:OpenLayerSelector - Unified Parametric Layer Selector & Inspector
;; =============================================================================
;; Parameters:
;;   filterPattern : Layer wildcard pattern (e.g., "R-LINE-*", "R-MAT-*", "R-*")
;;   dialogTitle   : Custom title/label for header (e.g., "Line Layer Selection...")
;;   defaultTool   : Default drawing tool ("PL", "REC", or nil for both)
;;   showHatch     : Boolean (T / nil) - Enables or disables Hatch specifications
;; Returns:
;;   (list actionType layerName) or nil if cancelled
;; =============================================================================
(defun CadSetup:OpenLayerSelector (filterPattern dialogTitle defaultTool showHatch /
                                   *error* matchingLayers ans dclPath dclId act
                                   acadApp acadDoc layersColl
                                   selIdx selLayer layObj curCol
                                   curTrans curHPat curHScl curHRot
                                   pendingTransMap ltList lwLabels lwValues
                                   updateDetails newCol selLtypeIdx selLwIdx
                                   rawVal rawScl defRow defCol defLt defLw
                                   defPlot defPat defScl defRot defTrans
                                   oldEcho item toolStr isAssignMode targetSS)
  (defun *error* (msg)
    (if (and dclId (>= dclId 0))
      (vl-catch-all-apply 'unload_dialog (list dclId))
    )
    (if (and msg (not (wcmatch (strcase msg t) "*break*,*cancel*,*exit*")))
      (princ (strcat "\n[UDLS Dialog Error]: " msg))
    )
    (princ)
  )

  ;; Detect Assign Mode from defaultTool
  (setq isAssignMode nil
        targetSS     nil)
  (cond
    ((and (listp defaultTool) (= (car defaultTool) :ASSIGN))
     (setq isAssignMode T
           targetSS     (cadr defaultTool)))
    ((and defaultTool (= (type defaultTool) 'STR) (or (= (strcase defaultTool) "ASSIGN") (= (strcase defaultTool) ":ASSIGN")))
     (setq isAssignMode T
           targetSS     (ssget "_I")))
  )

  ;; 1. Retrieve matching layers from active drawing
  (setq matchingLayers (CadSetup:GetDrawingLayersByPattern filterPattern))

  ;; 2. If no layers exist, prompt to load from database
  (if (null matchingLayers)
    (progn
      (initget "Yes No")
      (setq ans (getkword (strcat "\n[UDLS] No layers matching '" filterPattern "' found. Load standard layers from database? [Yes/No] <Yes>: ")))
      (if (or (null ans) (= ans "Yes") (= ans "Y"))
        (progn
          (princ (strcat "\n[UDLS] Loading layers for pattern '" filterPattern "' from database..."))
          (cond
            ((wcmatch (strcase filterPattern) "*LINE*")
             (CadSetup:EnsureLineLayersLoaded))
            ((wcmatch (strcase filterPattern) "*MAT*")
             (CadSetup:EnsureMaterialLayersLoaded))
            ((wcmatch (strcase filterPattern) "*ANNO*")
             (CadSetup:EnsureAnnotationLayersLoaded))
            ((wcmatch (strcase filterPattern) "*HARD*")
             (CadSetup:EnsureHardwareLayersLoaded))
            (t
             (if (boundp 'CadSetup:LoadAllLayers) (CadSetup:LoadAllLayers)))
          )
          (setq matchingLayers (CadSetup:GetDrawingLayersByPattern filterPattern))
        )
      )
    )
  )

  (if (null matchingLayers)
    (progn
      (princ (strcat "\n[UDLS] Cancelled. No layers matching '" filterPattern "' available."))
      (princ)
      nil
    )
    (progn
      (setq acadApp         (vlax-get-acad-object)
            acadDoc         (vla-get-activedocument acadApp)
            layersColl      (vla-get-layers acadDoc)
            pendingTransMap nil)

      ;; Lineweight definition mappings
      (setq lwLabels '("Default (-3)" "0.00 mm (0)" "0.05 mm (5)" "0.09 mm (9)" 
                       "0.13 mm (13)" "0.15 mm (15)" "0.18 mm (18)" "0.20 mm (20)" 
                       "0.25 mm (25)" "0.30 mm (30)" "0.35 mm (35)" "0.40 mm (40)" 
                       "0.50 mm (50)" "0.60 mm (60)" "0.70 mm (70)" "0.80 mm (80)" 
                       "0.90 mm (90)" "1.00 mm (100)" "1.20 mm (120)"))
      (setq lwValues '(-3 0 5 9 13 15 18 20 25 30 35 40 50 60 70 80 90 100 120))
      (setq ltList (CadSetup:GetLoadedLinetypes))

      ;; Locate UNIFIED-LAYER-SELECTOR.dcl
      (setq dclPath nil)
      (cond
        ((and (boundp 'CadSetup:GetDir) CadSetup:GetDir 
              (setq dclPath (strcat (CadSetup:GetDir) "\\UI\\UNIFIED-LAYER-SELECTOR.dcl")) 
              (findfile dclPath))
         dclPath)
        ((setq dclPath (findfile "UNIFIED-LAYER-SELECTOR.dcl"))
         dclPath)
        ((setq dclPath (findfile "UI\\UNIFIED-LAYER-SELECTOR.dcl"))
         dclPath)
        ((setq dclPath (findfile "d:\\Cad-Setup\\Cad-Setup-v4\\UI\\UNIFIED-LAYER-SELECTOR.dcl"))
         dclPath)
      )

      (if (or (null dclPath) (not (findfile dclPath)))
        (progn
          (princ "\n[UDLS Error]: UNIFIED-LAYER-SELECTOR.dcl not found in UI/ directory.")
          (exit)
        )
      )

      (setq dclId (load_dialog dclPath))
      (if (or (null dclId) (< dclId 0))
        (progn
          (princ (strcat "\n[UDLS Error]: Failed to load dialog file " dclPath))
          (exit)
        )
      )

      (if (not (new_dialog "unified_layer_selector_dialog" dclId))
        (progn
          (unload_dialog dclId)
          (princ "\n[UDLS Error]: Dialog definition 'unified_layer_selector_dialog' not found in DCL.")
          (exit)
        )
      )

      ;; Configure list box label
      (set_tile "box_layers_list" 
        (if isAssignMode
          (strcat "Assign to Selection (" filterPattern ")")
          (strcat "Available Layers (" filterPattern ")")
        )
      )

      ;; Populate layers listbox
      (start_list "lst_layers")
      (mapcar 'add_list matchingLayers)
      (end_list)

      ;; Populate Linetypes dropdown
      (start_list "pop_layer_ltype")
      (mapcar 'add_list ltList)
      (end_list)

      ;; Populate Lineweights dropdown
      (start_list "pop_layer_lweight")
      (mapcar 'add_list lwLabels)
      (end_list)

      ;; Selection state initialization
      (setq selIdx 0)
      (if (and *WF-LAYER-RL* (vl-position *WF-LAYER-RL* matchingLayers))
        (setq selIdx (vl-position *WF-LAYER-RL* matchingLayers))
      )
      (setq selLayer (nth selIdx matchingLayers))
      (set_tile "lst_layers" (itoa selIdx))

      ;; Details Updater Subroutine
      (defun updateDetails (layName / obj cVal ltp lwt plt dbRow desc swW swH posLtp posLwt descLines pendT)
        (setq obj (vl-catch-all-apply 'vla-item (list layersColl layName)))
        (if (and (not (vl-catch-all-error-p obj)) (= (type obj) 'VLA-OBJECT))
          (progn
            (setq layObj obj)
            (setq cVal (abs (vla-get-color layObj)))
            (setq curCol cVal)
            (setq ltp (vla-get-linetype layObj))
            (setq lwt (vla-get-lineweight layObj))
            (setq plt (= (vla-get-plottable layObj) :vlax-true))

            ;; Render Color Swatch
            (setq swW (dimx_tile "img_color_swatch")
                  swH (dimy_tile "img_color_swatch"))
            (start_image "img_color_swatch")
            (fill_image 0 0 swW swH cVal)
            (end_image)

            ;; Update textual tiles
            (set_tile "txt_layer_name" (strcat "Layer: " layName))
            (set_tile "txt_layer_color" (strcat "Color: " (itoa cVal) " (ACI)"))

            ;; Match and set Linetype popup
            (setq posLtp (vl-position (strcase ltp) (mapcar 'strcase ltList)))
            (if posLtp (set_tile "pop_layer_ltype" (itoa posLtp)))

            ;; Match and set Lineweight popup
            (setq posLwt (vl-position lwt lwValues))
            (if (null posLwt) (setq posLwt 0))
            (set_tile "pop_layer_lweight" (itoa posLwt))

            ;; Set Plottable toggle
            (set_tile "tog_layer_plot" (if plt "1" "0"))

            ;; Query in-memory and static Db_Layers specs
            (setq dbRow (if (boundp 'CadSetup:GetLayerData) (CadSetup:GetLayerData layName) nil))
            (if (null dbRow)
              (setq dbRow (assoc (strcase layName) (if (boundp '*CadSetup-Layers-Data*) *CadSetup-Layers-Data* nil)))
            )
            (if dbRow
              (progn
                (setq curHPat (if (nth 6 dbRow) (vl-princ-to-string (nth 6 dbRow)) "NONE")
                      curHScl (if (numberp (nth 7 dbRow)) (nth 7 dbRow) 1.0)
                      curHRot (if (numberp (nth 8 dbRow)) (nth 8 dbRow) 0.0)
                      curTrans (if (numberp (nth 9 dbRow)) (nth 9 dbRow) 0)
                      desc (if (nth 11 dbRow) (vl-princ-to-string (nth 11 dbRow)) ""))
              )
              (progn
                (setq curHPat "NONE" curHScl 1.0 curHRot 0.0 curTrans 0 desc "Custom Project Layer")
              )
            )

            ;; Check if transparency was edited in pending map
            (setq pendT (assoc layName pendingTransMap))
            (if pendT (setq curTrans (cdr pendT)))

            ;; Populate Hatch & Transparency tiles
            (set_tile "eb_layer_trans" (itoa curTrans))
            (set_tile "eb_hatch_pat" curHPat)
            (set_tile "eb_hatch_scl" (rtos curHScl 2 2))
            (set_tile "eb_hatch_rot" (rtos curHRot 2 1))

            ;; 3-Line Word-Wrapped Description
            (setq descLines (CadSetup:WrapText3Lines desc 52))
            (set_tile "txt_layer_desc1" (nth 0 descLines))
            (set_tile "txt_layer_desc2" (nth 1 descLines))
            (set_tile "txt_layer_desc3" (nth 2 descLines))
          )
        )
      )

      ;; Initial display population
      (updateDetails selLayer)

      ;; Configure Hatch specifications & Smart Auto-Hatch
      (if showHatch
        (progn
          (mode_tile "eb_hatch_pat" 0)
          (mode_tile "eb_hatch_scl" 0)
          (mode_tile "eb_hatch_rot" 0)
          (mode_tile "tog_auto_hatch" 0)
          (set_tile "tog_auto_hatch" (if *CadSetup-AutoHatch-Enabled* "1" "0"))
        )
        (progn
          (mode_tile "eb_hatch_pat" 1)
          (mode_tile "eb_hatch_scl" 1)
          (mode_tile "eb_hatch_rot" 1)
          (mode_tile "tog_auto_hatch" 1)
        )
      )

      ;; Configure Action Buttons based on defaultTool / isAssignMode
      (setq toolStr (if defaultTool (strcase (vl-princ-to-string (if (listp defaultTool) (car defaultTool) defaultTool))) ""))
      (cond
        (isAssignMode
         (mode_tile "btn_draw_pl" 1)
         (mode_tile "btn_draw_rec" 1)
         (set_tile "btn_current" "Assign to Selection")
         (mode_tile "btn_current" 0)
         (mode_tile "btn_current" 2) ; Set focus on Assign to Selection
        )
        ((or (= toolStr "PL") (= toolStr "POLYLINE") (= toolStr ":TOOL-PL"))
         (set_tile "btn_current" "Make Current Only")
         (mode_tile "btn_draw_pl" 0)
         (mode_tile "btn_draw_rec" 1)
         (mode_tile "btn_current" 0)
         (mode_tile "btn_draw_pl" 2) ; Set focus
        )
        ((or (= toolStr "REC") (= toolStr "RECTANGLE") (= toolStr ":TOOL-REC"))
         (set_tile "btn_current" "Make Current Only")
         (mode_tile "btn_draw_pl" 1)
         (mode_tile "btn_draw_rec" 0)
         (mode_tile "btn_current" 0)
         (mode_tile "btn_draw_rec" 2) ; Set focus
        )
        ((or (= toolStr "NONE") (= toolStr "CURRENT") (= toolStr ":CURRENT"))
         (set_tile "btn_current" "Make Current Only")
         (mode_tile "btn_draw_pl" 1)
         (mode_tile "btn_draw_rec" 1)
         (mode_tile "btn_current" 0)
         (mode_tile "btn_current" 2) ; Set focus
        )
        (t
         ;; defaultTool is nil - both drawing buttons active
         (set_tile "btn_current" "Make Current Only")
         (mode_tile "btn_draw_pl" 0)
         (mode_tile "btn_draw_rec" 0)
         (mode_tile "btn_current" 0)
        )
      )

      ;; Event Handlers
      (action_tile "tog_auto_hatch"
        "(setq *CadSetup-AutoHatch-Enabled* (= $value \"1\"))"
      )

      (action_tile "lst_layers"
        "(setq selIdx (atoi $value)
               selLayer (nth selIdx matchingLayers))
         (updateDetails selLayer)
         (if (= $reason 4)
           (cond
             (isAssignMode
              (done_dialog 4))
             ((or (= toolStr \"NONE\") (= toolStr \"CURRENT\") (= toolStr \":CURRENT\"))
              (done_dialog 3))
             ((or (= toolStr \"REC\") (= toolStr \"RECTANGLE\") (= toolStr \":TOOL-REC\"))
              (done_dialog 2))
             (t
              (done_dialog 1))
           )
         )"
      )

      (action_tile "btn_edit_color"
        "(if layObj
           (progn
             (setq newCol (acad_colordlg curCol nil))
             (if (and newCol (numberp newCol))
               (progn
                 (vla-put-color layObj newCol)
                 (setq curCol newCol)
                 (updateDetails selLayer)
               )
             )
           )
         )"
      )

      (action_tile "pop_layer_ltype"
        "(if layObj
           (progn
             (setq selLtypeIdx (atoi $value))
             (if (and (>= selLtypeIdx 0) (< selLtypeIdx (length ltList)))
               (vl-catch-all-apply 'vla-put-linetype (list layObj (nth selLtypeIdx ltList)))
             )
           )
         )"
      )

      (action_tile "pop_layer_lweight"
        "(if layObj
           (progn
             (setq selLwIdx (atoi $value))
             (if (and (>= selLwIdx 0) (< selLwIdx (length lwValues)))
               (vl-catch-all-apply 'vla-put-lineweight (list layObj (nth selLwIdx lwValues)))
             )
           )
         )"
      )

      (action_tile "tog_layer_plot"
        "(if layObj
           (vla-put-plottable layObj (if (= $value \"1\") :vlax-true :vlax-false))
         )"
      )

      (action_tile "eb_layer_trans"
        "(setq rawVal (atoi $value))
         (if (< rawVal 0) (setq rawVal 0))
         (if (> rawVal 90) (setq rawVal 90))
         (set_tile \"eb_layer_trans\" (itoa rawVal))
         (setq curTrans rawVal)
         (setq pendingTransMap (cons (cons selLayer curTrans) 
                                     (vl-remove-if (function (lambda (x) (= (car x) selLayer))) pendingTransMap)))
         (CadSetup:UpdateLayerDataInMemory selLayer nil nil nil curTrans)"
      )

      (action_tile "eb_hatch_pat"
        "(setq curHPat (strcase (vl-string-trim \" \" $value)))
         (CadSetup:UpdateLayerDataInMemory selLayer curHPat nil nil nil)"
      )

      (action_tile "eb_hatch_scl"
        "(setq rawScl (distof $value))
         (if (and rawScl (> rawScl 0.0))
           (progn
             (setq curHScl rawScl)
             (CadSetup:UpdateLayerDataInMemory selLayer nil curHScl nil nil)
           )
           (set_tile \"eb_hatch_scl\" (rtos curHScl 2 2))
         )"
      )

      (action_tile "eb_hatch_rot"
        "(setq rawScl (distof $value))
         (if rawScl
           (progn
             (setq curHRot rawScl)
             (CadSetup:UpdateLayerDataInMemory selLayer nil nil curHRot nil)
           )
           (set_tile \"eb_hatch_rot\" (rtos curHRot 2 1))
         )"
      )

      (action_tile "btn_reset_defaults"
        "(if (boundp '*CadSetup-Master-Layers-Backup*)
           (setq defRow (assoc (strcase selLayer) *CadSetup-Master-Layers-Backup*))
           (setq defRow nil)
         )
         (if defRow
           (progn
             (setq defCol   (if (numberp (nth 1 defRow)) (nth 1 defRow) 7)
                   defLt    (if (nth 3 defRow) (vl-princ-to-string (nth 3 defRow)) \"CONTINUOUS\")
                   defLw    (if (numberp (nth 4 defRow)) (nth 4 defRow) 25)
                   defPlot  (nth 5 defRow)
                   defPat   (if (nth 6 defRow) (vl-princ-to-string (nth 6 defRow)) \"NONE\")
                   defScl   (if (numberp (nth 7 defRow)) (nth 7 defRow) 1.0)
                   defRot   (if (numberp (nth 8 defRow)) (nth 8 defRow) 0.0)
                   defTrans (if (numberp (nth 9 defRow)) (nth 9 defRow) 0))

             (if layObj
               (progn
                 (vla-put-color layObj defCol)
                 (vl-catch-all-apply 'vla-put-linetype (list layObj defLt))
                 (vl-catch-all-apply 'vla-put-lineweight (list layObj defLw))
                 (vla-put-plottable layObj (if defPlot :vlax-true :vlax-false))
               )
             )
             (setq curTrans defTrans)
             (setq pendingTransMap (cons (cons selLayer curTrans) 
                                         (vl-remove-if (function (lambda (x) (= (car x) selLayer))) pendingTransMap)))
             (CadSetup:UpdateLayerDataInMemory selLayer defPat defScl defRot defTrans)
             (updateDetails selLayer)
             (princ (strcat \"\\n[UDLS] Reset \" selLayer \" to standard database defaults.\"))
           )
           (princ (strcat \"\\n[UDLS] No default definition found for \" selLayer))
         )"
      )

      (action_tile "btn_draw_pl" "(done_dialog 1)")
      (action_tile "btn_draw_rec" "(done_dialog 2)")
      (action_tile "btn_current"
        (if isAssignMode
          "(done_dialog 4)"
          "(done_dialog 3)"
        )
      )
      (action_tile "cancel" "(done_dialog 0)")

      (setq act (start_dialog))
      (unload_dialog dclId)

      ;; Apply modified transparencies natively outside DCL
      (if pendingTransMap
        (progn
          (setq oldEcho (getvar "CMDECHO"))
          (setvar "CMDECHO" 0)
          (foreach item pendingTransMap
            (vl-catch-all-apply
              (function (lambda ()
                (command "._-LAYER" "_TR" (itoa (cdr item)) (car item) "")
              ))
            )
          )
          (setvar "CMDECHO" oldEcho)
        )
      )

      ;; Direct tool execution based on dialog action
      (cond
        ((= act 4)
         (if targetSS
           (CadSetup:AssignEntitiesToLayer targetSS selLayer)
           (princ (strcat "\n[UDLS] Target layer selected: " selLayer))
         )
         (list :assign selLayer)
        )
        ((= act 1)
         (CadSetup:DrawPolyline selLayer)
         (list :draw-pl selLayer)
        )
        ((= act 2)
         (CadSetup:DrawRectangle selLayer)
         (list :draw-rec selLayer)
        )
        ((= act 3)
         (CadSetup:SetCurrentLayerSafe selLayer)
         (setq *WF-LAYER-RL* selLayer)
         (if (wcmatch (strcase selLayer) "R-ANNO-*")
           (setq *WF-LAYER-AD* selLayer)
         )
         (if (wcmatch (strcase selLayer) "R-HARD-*")
           (setq *WF-LAYER-HD* selLayer)
         )
         (princ (strcat "\n[UDLS] Current layer set to: " selLayer))
         (list :current selLayer)
        )
        (t nil)
      )
    )
  )
)

;; Backward compatibility aliases for old dialog functions
(defun CadSetup:LineSelectorDialog (lineLayers)
  (CadSetup:OpenLayerSelector "R-LINE-*" "Line Layer Selection && Property Inspector" "PL" nil)
)

(defun CadSetup:MaterialSelectorDialog (matLayers)
  (CadSetup:OpenLayerSelector "R-MAT-*" "Material Selection && Property Inspector" "REC" T)
)

(defun CadSetup:AnnotationSelectorDialog (annoLayers)
  (CadSetup:OpenLayerSelector "R-ANNO-*" "Annotation & Dim Layer Selection && Property Inspector" ":CURRENT" nil)
)

(defun CadSetup:HardwareSelectorDialog (hardLayers)
  (CadSetup:OpenLayerSelector "R-HARD-*" "Hardware & Fittings Layer Selection && Property Inspector" ":CURRENT" nil)
)

(defun CadSetup:RLayerSelectorDialog (rLayers)
  (CadSetup:OpenLayerSelector "R-*" "R-Layer Selection && Property Inspector" nil T)
)

;; CadSetup:GetLayerPromptSuffix - Extracts clean command-line suffix for layer prompt
(defun CadSetup:GetLayerPromptSuffix (layName filterPattern)
  (cond
    ((wcmatch (strcase filterPattern) "*LINE*")
     (if (> (strlen layName) 7) (substr layName 8) layName))
    ((wcmatch (strcase filterPattern) "*MAT*")
     (if (> (strlen layName) 6) (substr layName 7) layName))
    ((wcmatch (strcase filterPattern) "*ANNO*")
     (if (> (strlen layName) 7) (substr layName 8) layName))
    ((wcmatch (strcase filterPattern) "*HARD*")
     (if (> (strlen layName) 7) (substr layName 8) layName))
    ((wcmatch (strcase filterPattern) "R-*")
     (if (> (strlen layName) 2) (substr layName 3) layName))
    (t
     layName)
  )
)

;; CadSetup:PromptAndAssignLayer - Generalized interactive layer selector & assignment for pre-selected objects
;; Parameters:
;;   ss            : Implied selection set (ssget "_I") or picked selection set
;;   filterPattern : Layer wildcard pattern (e.g. "R-LINE-*", "R-MAT-*", "R-ANNO-*", "R-HARD-*", "R-*")
;;   categoryLabel : Human-readable category string (e.g. "Line", "Material", "Annotation", "Hardware", "R-Layer")
;;   showHatch     : Boolean flag whether to show hatch specs in DCL dialog (T for materials/R-layers, nil otherwise)
(defun CadSetup:PromptAndAssignLayer (ss filterPattern categoryLabel showHatch /
                                      matchingLayers kwMap promptStr kwStr suffix kw opt chosenLayer)
  (setq matchingLayers (CadSetup:GetDrawingLayersByPattern filterPattern))

  (if (null matchingLayers)
    (CadSetup:OpenLayerSelector filterPattern (strcat "Assign " categoryLabel " Layer to Selection") (list :ASSIGN ss) showHatch)
    (progn
      ;; Build Command-Line Keywords and Prompt Map
      (setq kwMap '(("DIALOG" . "DIALOG") ("D" . "DIALOG")))
      (setq kwStr "Dialog D")

      (if showHatch
        (progn
          (setq kwMap (cons '("AUTOHATCH" . "AUTOHATCH")
                            (cons '("AH" . "AUTOHATCH")
                                  (cons '("A" . "AUTOHATCH") kwMap))))
          (setq kwStr (strcat kwStr " AutoHatch AH A"))
        )
      )

      (foreach lay matchingLayers
        (setq suffix (CadSetup:GetLayerPromptSuffix lay filterPattern))
        (setq kw (strcase (vl-string-translate " " "_" suffix)))
        (setq kwMap (cons (cons kw lay) kwMap))
        (setq kwStr (strcat kwStr " " kw))
      )

      (if showHatch
        (progn
          (setq opt "AUTOHATCH")
          (while (and opt (or (= (strcase opt) "AUTOHATCH") (= (strcase opt) "AH") (= (strcase opt) "A")))
            (setq promptStr (strcat "\nAssign " categoryLabel " to Selection (AutoHatch: " (if *CadSetup-AutoHatch-Enabled* "ON" "OFF") ") [Dialog/AutoHatch"))
            (foreach lay matchingLayers
              (setq suffix (CadSetup:GetLayerPromptSuffix lay filterPattern))
              (setq promptStr (strcat promptStr "/" suffix))
            )
            (setq promptStr (strcat promptStr "] <Dialog>: "))

            (initget kwStr)
            (setq opt (getkword promptStr))

            (if (and opt (or (= (strcase opt) "AUTOHATCH") (= (strcase opt) "AH") (= (strcase opt) "A")))
              (progn
                (setq *CadSetup-AutoHatch-Enabled* (not *CadSetup-AutoHatch-Enabled*))
                (princ (strcat "\n[" categoryLabel "] Smart Auto-Hatch is now " (if *CadSetup-AutoHatch-Enabled* "ON" "OFF") "."))
              )
            )
          )
        )
        (progn
          (setq promptStr (strcat "\nAssign " categoryLabel " to Selection [Dialog"))
          (foreach lay matchingLayers
            (setq suffix (CadSetup:GetLayerPromptSuffix lay filterPattern))
            (setq promptStr (strcat promptStr "/" suffix))
          )
          (setq promptStr (strcat promptStr "] <Dialog>: "))

          (initget kwStr)
          (setq opt (getkword promptStr))
        )
      )

      (if (or (null opt) (= (strcase opt) "DIALOG") (= (strcase opt) "D"))
        (CadSetup:OpenLayerSelector filterPattern (strcat "Assign " categoryLabel " Layer to Selection") (list :ASSIGN ss) showHatch)
        (progn
          (setq chosenLayer (cdr (assoc (strcase (vl-string-translate " " "_" opt)) kwMap)))
          (if chosenLayer
            (CadSetup:AssignEntitiesToLayer ss chosenLayer)
            (princ (strcat "\n[" categoryLabel "] Unrecognized layer: " opt))
          )
        )
      )
    )
  )
  (princ)
)


;;; --------------------------------------------------------------------------
;;; 5. COMMAND ENTRY POINTS (LL, ML, -, 4, 5, R-, RLAY)
;;; --------------------------------------------------------------------------

;; c:LL - Line Layer / Polyline Workflow Entry Point
(defun c:LL ( / ss lineLayers promptStr kwStr kwMap suffix kw opt chosenLayer )
  (setq ss (ssget "_I"))
  (if (and ss (> (sslength ss) 0))
    (CadSetup:PromptAndAssignLayer ss "R-LINE-*" "Line" nil)
    (progn
      (setq lineLayers (CadSetup:GetDrawingLayersByPattern "R-LINE-*"))

      (if (null lineLayers)
        (CadSetup:OpenLayerSelector "R-LINE-*" "Line Layer Selection && Property Inspector" "PL" nil)
        (progn
          ;; Build Command-Line Keywords and Prompt Map
          (setq kwMap '(("DIALOG" . "DIALOG") ("D" . "DIALOG")))
          (setq promptStr "\nSelect Line [Dialog")
          (setq kwStr "Dialog D")

          (foreach lay lineLayers
            (setq suffix (if (> (strlen lay) 7) (substr lay 8) lay))
            (setq kw (strcase (vl-string-translate " " "_" suffix)))
            (setq kwMap (cons (cons kw lay) kwMap))
            (setq promptStr (strcat promptStr "/" suffix))
            (setq kwStr (strcat kwStr " " kw))
          )
          (setq promptStr (strcat promptStr "] <Dialog>: "))

          (initget kwStr)
          (setq opt (getkword promptStr))

          (if (or (null opt) (= (strcase opt) "DIALOG") (= (strcase opt) "D"))
            (CadSetup:OpenLayerSelector "R-LINE-*" "Line Layer Selection && Property Inspector" "PL" nil)
            (progn
              (setq chosenLayer (cdr (assoc (strcase (vl-string-translate " " "_" opt)) kwMap)))
              (if chosenLayer
                (CadSetup:DrawPolyline chosenLayer)
                (princ (strcat "\n[LL] Unrecognized line layer: " opt))
              )
            )
          )
        )
      )
    )
  )
  (princ)
)

(defun c:4 () (c:LL))


;; c:ML - Material Layer / Rectangle Workflow Entry Point
(defun c:ML ( / ss matLayers promptStr kwStr kwMap suffix kw opt chosenLayer )
  (setq ss (ssget "_I"))
  (if (and ss (> (sslength ss) 0))
    (CadSetup:PromptAndAssignLayer ss "R-MAT-*" "Material" T)
    (progn
      (setq matLayers (CadSetup:GetDrawingLayersByPattern "R-MAT-*"))

      (if (null matLayers)
        (CadSetup:OpenLayerSelector "R-MAT-*" "Material Selection && Property Inspector" "REC" T)
        (progn
          (setq kwMap '(("DIALOG" . "DIALOG") ("D" . "DIALOG")
                        ("AUTOHATCH" . "AUTOHATCH") ("AH" . "AUTOHATCH") ("A" . "AUTOHATCH")))
          (setq kwStr "Dialog D AutoHatch AH A")

          (foreach lay matLayers
            (setq suffix (if (> (strlen lay) 6) (substr lay 7) lay))
            (setq kw (strcase (vl-string-translate " " "_" suffix)))
            (setq kwMap (cons (cons kw lay) kwMap))
            (setq kwStr (strcat kwStr " " kw))
          )

          (setq opt "AUTOHATCH")
          (while (and opt (or (= (strcase opt) "AUTOHATCH") (= (strcase opt) "AH") (= (strcase opt) "A")))
            (setq promptStr (strcat "\nSelect Material (AutoHatch: " (if *CadSetup-AutoHatch-Enabled* "ON" "OFF") ") [Dialog/AutoHatch"))
            (foreach lay matLayers
              (setq suffix (if (> (strlen lay) 6) (substr lay 7) lay))
              (setq promptStr (strcat promptStr "/" suffix))
            )
            (setq promptStr (strcat promptStr "] <Dialog>: "))

            (initget kwStr)
            (setq opt (getkword promptStr))

            (if (and opt (or (= (strcase opt) "AUTOHATCH") (= (strcase opt) "AH") (= (strcase opt) "A")))
              (progn
                (setq *CadSetup-AutoHatch-Enabled* (not *CadSetup-AutoHatch-Enabled*))
                (princ (strcat "\n[ML] Smart Auto-Hatch is now " (if *CadSetup-AutoHatch-Enabled* "ON" "OFF") "."))
              )
            )
          )

          (if (or (null opt) (= (strcase opt) "DIALOG") (= (strcase opt) "D"))
            (CadSetup:OpenLayerSelector "R-MAT-*" "Material Selection && Property Inspector" "REC" T)
            (progn
              (setq chosenLayer (cdr (assoc (strcase (vl-string-translate " " "_" opt)) kwMap)))
              (if chosenLayer
                (CadSetup:DrawRectangle chosenLayer)
                (princ (strcat "\n[ML] Unrecognized material: " opt))
              )
            )
          )
        )
      )
    )
  )
  (princ)
)

(defun c:5 () (c:ML))


;; c:AD - Annotation & Dim Suite / Layer Selection Entry Point
(defun c:AD ( / ss *error* annoLayers promptStr kwStr kwMap suffix kw opt chosenLayer dbRow desc )
  (setq ss (ssget "_I"))
  (if (and ss (> (sslength ss) 0))
    (CadSetup:PromptAndAssignLayer ss "R-ANNO-*" "Annotation" nil)
    (progn
      (defun *error* (msg)
        (if (boundp 'CadSetup:UndoReset) (CadSetup:UndoReset))
        (if (and msg (not (wcmatch (strcase msg t) "*break*,*cancel*,*exit*")))
          (princ (strcat "\n[AD] Error: " msg))
        )
        (princ)
      )

      (setq annoLayers (CadSetup:GetDrawingLayersByPattern "R-ANNO-*"))

      (if (null annoLayers)
        (CadSetup:OpenLayerSelector "R-ANNO-*" "Annotation & Dim Layer Selection && Property Inspector" ":CURRENT" nil)
        (progn
          ;; Build Command-Line Keywords and Prompt Map
          (setq kwMap '(("DIALOG" . "DIALOG") ("D" . "DIALOG")))
          (setq promptStr "\nSelect Annotation [Dialog")
          (setq kwStr "Dialog D")

          (foreach lay annoLayers
            ;; Layer names format: "R-ANNO-DIMS" -> suffix "DIMS" (length 7 prefix "R-ANNO-")
            (setq suffix (if (> (strlen lay) 7) (substr lay 8) lay))
            (setq kw (strcase (vl-string-translate " " "_" suffix)))
            (setq kwMap (cons (cons kw lay) kwMap))
            (setq promptStr (strcat promptStr "/" suffix))
            (setq kwStr (strcat kwStr " " kw))
          )
          (setq promptStr (strcat promptStr "] <Dialog>: "))

          (initget kwStr)
          (setq opt (getkword promptStr))

          (if (or (null opt) (= (strcase opt) "DIALOG") (= (strcase opt) "D"))
            (CadSetup:OpenLayerSelector "R-ANNO-*" "Annotation & Dim Layer Selection && Property Inspector" ":CURRENT" nil)
            (progn
              (setq chosenLayer (cdr (assoc (strcase (vl-string-translate " " "_" opt)) kwMap)))
              (if chosenLayer
                (progn
                  (if (boundp 'CadSetup:UndoStart) (CadSetup:UndoStart))
                  (CadSetup:SetCurrentLayerSafe chosenLayer)
                  (setq *WF-LAYER-AD* chosenLayer
                        *WF-LAYER-RL* chosenLayer)
                  (setq dbRow (if (boundp 'CadSetup:GetLayerData) (CadSetup:GetLayerData chosenLayer) nil))
                  (setq desc (if (and dbRow (nth 11 dbRow)) (vl-princ-to-string (nth 11 dbRow)) ""))
                  (if (boundp 'CadSetup:UndoEnd) (CadSetup:UndoEnd))
                  (princ (strcat "\n[AD] Active layer set to: " chosenLayer
                                 (if (/= desc "") (strcat " (" desc ")") "")))
                )
                (princ (strcat "\n[AD] Unrecognized annotation layer: " opt))
              )
            )
          )
        )
      )
    )
  )
  (princ)
)

(defun c:6 () (c:AD))


;; c:HD - Hardware & Fittings / Layer Selection Entry Point
(defun c:HD ( / ss *error* hardLayers promptStr kwStr kwMap suffix kw opt chosenLayer dbRow desc )
  (setq ss (ssget "_I"))
  (if (and ss (> (sslength ss) 0))
    (CadSetup:PromptAndAssignLayer ss "R-HARD-*" "Hardware" nil)
    (progn
      (defun *error* (msg)
        (if (boundp 'CadSetup:UndoReset) (CadSetup:UndoReset))
        (if (and msg (not (wcmatch (strcase msg t) "*break*,*cancel*,*exit*")))
          (princ (strcat "\n[HD] Error: " msg))
        )
        (princ)
      )

      (setq hardLayers (CadSetup:GetDrawingLayersByPattern "R-HARD-*"))

      (if (null hardLayers)
        (CadSetup:OpenLayerSelector "R-HARD-*" "Hardware & Fittings Layer Selection && Property Inspector" ":CURRENT" nil)
        (progn
          ;; Build Command-Line Keywords and Prompt Map
          (setq kwMap '(("DIALOG" . "DIALOG") ("D" . "DIALOG")))
          (setq promptStr "\nSelect Hardware [Dialog")
          (setq kwStr "Dialog D")

          (foreach lay hardLayers
            ;; Layer names format: "R-HARD-FITTINGS" -> suffix "FITTINGS" (length 7 prefix "R-HARD-")
            (setq suffix (if (> (strlen lay) 7) (substr lay 8) lay))
            (setq kw (strcase (vl-string-translate " " "_" suffix)))
            (setq kwMap (cons (cons kw lay) kwMap))
            (setq promptStr (strcat promptStr "/" suffix))
            (setq kwStr (strcat kwStr " " kw))
          )
          (setq promptStr (strcat promptStr "] <Dialog>: "))

          (initget kwStr)
          (setq opt (getkword promptStr))

          (if (or (null opt) (= (strcase opt) "DIALOG") (= (strcase opt) "D"))
            (CadSetup:OpenLayerSelector "R-HARD-*" "Hardware & Fittings Layer Selection && Property Inspector" ":CURRENT" nil)
            (progn
              (setq chosenLayer (cdr (assoc (strcase (vl-string-translate " " "_" opt)) kwMap)))
              (if chosenLayer
                (progn
                  (if (boundp 'CadSetup:UndoStart) (CadSetup:UndoStart))
                  (CadSetup:SetCurrentLayerSafe chosenLayer)
                  (setq *WF-LAYER-HD* chosenLayer
                        *WF-LAYER-RL* chosenLayer)
                  (setq dbRow (if (boundp 'CadSetup:GetLayerData) (CadSetup:GetLayerData chosenLayer) nil))
                  (setq desc (if (and dbRow (nth 11 dbRow)) (vl-princ-to-string (nth 11 dbRow)) ""))
                  (if (boundp 'CadSetup:UndoEnd) (CadSetup:UndoEnd))
                  (princ (strcat "\n[HD] Active layer set to: " chosenLayer
                                 (if (/= desc "") (strcat " (" desc ")") "")))
                )
                (princ (strcat "\n[HD] Unrecognized hardware layer: " opt))
              )
            )
          )
        )
      )
    )
  )
  (princ)
)

(defun c:7 () (c:HD))

;; Key 8: Blocks & Components Palette (Delegates to CadSetup:OpenBlockPalette)
(defun c:BL ()
  (if (boundp 'CadSetup:OpenBlockPalette)
    (CadSetup:OpenBlockPalette)
    (princ "\n[BL] Block Palette module not loaded.")
  )
  (princ)
)
(defun c:8 () (c:BL))

;;; --------------------------------------------------------------------------
;;; WORKFLOW KEY 0: LAYER 0 & BYLAYER NORMALIZER (0 / L0 / BY0)
;;; --------------------------------------------------------------------------
;; Dual-mode operation:
;;   1. If objects are pre-selected (Pickfirst) or selected via prompt, moves them
;;      to Layer "0" and resets all properties (Color, Linetype, Lineweight,
;;      Linetype Scale, Global Polyline Width, Thickness, Transparency) to ByLayer
;;      and standard defaults, deeply normalizing nested block definitions.
;;   2. Always switches active layer (CLAYER) to "0" and resets drawing defaults
;;      (CECOLOR, CELTYPE, CELWEIGHT, CELTSCALE, PLINEWID, THICKNESS, CETRANSPARENCY)
;;      to ByLayer / default values.
;;   3. Retains selection for immediate follow-up operations.

;; Direct fallback normalizer if Help_Layers.lsp is not yet loaded
(defun CadSetup:NormalizeSelectionDirect (ss / i ent obj resPut coords n)
  (if (and ss (= (type ss) 'PICKSET))
    (progn
      (setq i 0)
      (while (< i (sslength ss))
        (setq ent (ssname ss i))
        (setq obj (vl-catch-all-apply 'vlax-ename->vla-object (list ent)))
        (if (and obj (not (vl-catch-all-error-p obj)) (= (type obj) 'VLA-OBJECT))
          (progn
            ;; Layer: "0"
            (vl-catch-all-apply 'vla-put-layer (list obj "0"))
            ;; Color: ByLayer (256)
            (vl-catch-all-apply 'vla-put-color (list obj 256))
            ;; Linetype: "ByLayer"
            (vl-catch-all-apply 'vla-put-linetype (list obj "ByLayer"))
            ;; Lineweight: ByLayer (-1)
            (if (vlax-property-available-p obj 'Lineweight)
              (vl-catch-all-apply 'vla-put-lineweight (list obj -1))
            )
            ;; Linetype Scale (linescale): 1.0
            (if (vlax-property-available-p obj 'LinetypeScale)
              (vl-catch-all-apply 'vla-put-linetypescale (list obj 1.0))
            )
            ;; Global Width (polyline constant width): 0.0
            (if (vlax-property-available-p obj 'ConstantWidth)
              (progn
                (setq resPut (vl-catch-all-apply 'vla-put-constantwidth (list obj 0.0)))
                (if (vl-catch-all-error-p resPut)
                  (vl-catch-all-apply
                    '(lambda ( / coords n )
                       (setq coords (vlax-get obj 'Coordinates))
                       (if coords
                         (progn
                           (setq n 0)
                           (while (< n (/ (length coords) 2))
                             (vl-catch-all-apply 'vla-setwidth (list obj n 0.0 0.0))
                             (setq n (1+ n))
                           )
                         )
                       )
                     )
                  )
                )
              )
            )
            ;; Heavy 2D Polyline vertex widths: 0.0
            (if (= (vla-get-objectname obj) "AcDb2dPolyline")
              (progn
                (vl-catch-all-apply 'vla-put-defaultstartwidth (list obj 0.0))
                (vl-catch-all-apply 'vla-put-defaultendwidth (list obj 0.0))
                (vlax-for vtx obj
                  (if (= (vla-get-objectname vtx) "AcDb2dVertex")
                    (progn
                      (vl-catch-all-apply 'vla-put-startwidth (list vtx 0.0))
                      (vl-catch-all-apply 'vla-put-endwidth (list vtx 0.0))
                    )
                  )
                )
              )
            )
            ;; Transparency: "ByLayer"
            (if (vlax-property-available-p obj 'Transparency)
              (vl-catch-all-apply 'vla-put-transparency (list obj "ByLayer"))
            )
            ;; PlotStyleName: "ByLayer"
            (if (vlax-property-available-p obj 'PlotStyleName)
              (vl-catch-all-apply 'vla-put-plotstylename (list obj "ByLayer"))
            )
            ;; Material: "ByLayer"
            (if (vlax-property-available-p obj 'Material)
              (vl-catch-all-apply 'vla-put-material (list obj "ByLayer"))
            )
            ;; Thickness: 0.0
            (if (vlax-property-available-p obj 'Thickness)
              (vl-catch-all-apply 'vla-put-thickness (list obj 0.0))
            )
          )
        )
        (setq i (1+ i))
      )
    )
  )
)

(defun c:L0 ( / *error* ss count oldEcho )
  (defun *error* (msg)
    (if (boundp 'CadSetup:UndoReset) (CadSetup:UndoReset))
    (if (and msg (not (wcmatch (strcase msg t) "*break*,*cancel*,*exit*")))
      (princ (strcat "\n[L0] Error: " msg))
    )
    (princ)
  )

  (setq oldEcho (getvar "CMDECHO"))
  (setvar "CMDECHO" 0)

  ;; Ensure Layer "0" is ready (unlocked, thawed, ON)
  (if (boundp 'CadSetup:EnsureLayerReady)
    (CadSetup:EnsureLayerReady "0")
  )

  ;; Step 1: Detect active selection (Pickfirst) or prompt user
  (setq ss (ssget "_I"))
  (if (or (null ss) (= (sslength ss) 0))
    (progn
      (princ "\nSelect objects to reset to Layer 0 & ByLayer (or press Enter to switch active layer only): ")
      (setq ss (ssget))
    )
  )

  ;; Step 2: Normalize selected geometry if any
  (if (and ss (> (sslength ss) 0))
    (progn
      (if (and (not (boundp 'CadSetup:NormalizeToLayer0ByLayer))
               (boundp 'CadSetup:GetDir)
               CadSetup:GetDir)
        (vl-catch-all-apply 'load (list (strcat (CadSetup:GetDir) "\\Helpers\\Help_Layers.lsp")))
      )
      (if (boundp 'CadSetup:NormalizeToLayer0ByLayer)
        (CadSetup:NormalizeToLayer0ByLayer ss T)
        (CadSetup:NormalizeSelectionDirect ss)
      )
    )
  )

  ;; Step 3: Switch current drafting layer and object defaults
  (setvar "CLAYER" "0")
  (setvar "CECOLOR" "BYLAYER")
  (setvar "CELTYPE" "BYLAYER")
  (setvar "CELWEIGHT" -1)
  (vl-catch-all-apply 'setvar (list "CELTSCALE" 1.0))
  (vl-catch-all-apply 'setvar (list "PLINEWID" 0.0))
  (vl-catch-all-apply 'setvar (list "THICKNESS" 0.0))
  (vl-catch-all-apply 'setvar (list "CETRANSPARENCY" "ByLayer"))

  (if ss (sssetfirst nil ss))

  (princ "\n[L0] Active layer set to \"0\". Defaults locked to ByLayer (Linescale=1.0, Width=0.0).")
  (setvar "CMDECHO" oldEcho)
  (princ)
)

(defun c:0   () (c:L0))
(defun c:BY0 () (c:L0))


;;; --------------------------------------------------------------------------
;;; 6. ALL R-LAYERS SELECTOR & GEOMETRY DRAWING (` / - / R- / RLAY)
;;; --------------------------------------------------------------------------

;; CadSetup:GetDrawingRLayers - Returns a sorted list of all active drawing layers matching "R-*"
(defun CadSetup:GetDrawingRLayers ( / layEntry layList )
  (setq layList nil)
  (setq layEntry (tblnext "LAYER" t))
  (while layEntry
    (if (wcmatch (strcase (cdr (assoc 2 layEntry))) "R-*")
      (setq layList (cons (cdr (assoc 2 layEntry)) layList))
    )
    (setq layEntry (tblnext "LAYER" nil))
  )
  (if layList
    (acad_strlsort layList)
    nil
  )
)

;; CadSetup:DrawRLayerPolyline - Sets current layer, records state, and launches Polyline
(defun CadSetup:DrawRLayerPolyline (layName)
  (CadSetup:DrawPolyline layName)
)

;; CadSetup:DrawRLayerRectangles - Sets current layer, records state, and launches Rectangle
(defun CadSetup:DrawRLayerRectangles (layName)
  (CadSetup:DrawRectangle layName)
)

;; CadSetup:RLayerSelectorDialog - Modal DCL controller for selecting and editing R-* layer properties
(defun CadSetup:RLayerSelectorDialog (rLayers / *error* dclPath dclId act
                                                acadApp acadDoc layersColl
                                                selIdx selLayer layObj curCol
                                                curTrans curHPat curHScl curHRot
                                                pendingTransMap ltList lwLabels lwValues
                                                updateDetails newCol selLtypeIdx selLwIdx
                                                rawVal rawScl defRow defCol defLt defLw
                                                defPlot defPat defScl defRot defTrans
                                                oldEcho item)
  (defun *error* (msg)
    (if (and dclId (>= dclId 0))
      (vl-catch-all-apply 'unload_dialog (list dclId))
    )
    (if (and msg (not (wcmatch (strcase msg t) "*break*,*cancel*,*exit*")))
      (princ (strcat "\n[- Dialog Error]: " msg))
    )
    (princ)
  )

  (setq acadApp         (vlax-get-acad-object)
        acadDoc         (vla-get-activedocument acadApp)
        layersColl      (vla-get-layers acadDoc)
        pendingTransMap nil)

  ;; Lineweight definition mappings
  (setq lwLabels '("Default (-3)" "0.00 mm (0)" "0.05 mm (5)" "0.09 mm (9)" 
                   "0.13 mm (13)" "0.15 mm (15)" "0.18 mm (18)" "0.20 mm (20)" 
                   "0.25 mm (25)" "0.30 mm (30)" "0.35 mm (35)" "0.40 mm (40)" 
                   "0.50 mm (50)" "0.60 mm (60)" "0.70 mm (70)" "0.80 mm (80)" 
                   "0.90 mm (90)" "1.00 mm (100)" "1.20 mm (120)"))
  (setq lwValues '(-3 0 5 9 13 15 18 20 25 30 35 40 50 60 70 80 90 100 120))
  (setq ltList (CadSetup:GetLoadedLinetypes))

  ;; Locate R-LAYER-SELECTOR.dcl
  (setq dclPath nil)
  (cond
    ((and (boundp 'CadSetup:GetDir) CadSetup:GetDir 
          (setq dclPath (strcat (CadSetup:GetDir) "\\UI\\R-LAYER-SELECTOR.dcl")) 
          (findfile dclPath))
     dclPath)
    ((setq dclPath (findfile "R-LAYER-SELECTOR.dcl"))
     dclPath)
    ((setq dclPath (findfile "UI\\R-LAYER-SELECTOR.dcl"))
     dclPath)
    ((setq dclPath (findfile "d:\\Cad-Setup\\Cad-Setup-v4\\UI\\R-LAYER-SELECTOR.dcl"))
     dclPath)
  )

  (if (or (null dclPath) (not (findfile dclPath)))
    (progn
      (princ "\n[-] Error: R-LAYER-SELECTOR.dcl not found in UI/ directory.")
      (exit)
    )
  )

  (setq dclId (load_dialog dclPath))
  (if (or (null dclId) (< dclId 0))
    (progn
      (princ (strcat "\n[-] Error: Failed to load dialog file " dclPath))
      (exit)
    )
  )

  (if (not (new_dialog "r_layer_selector_dialog" dclId))
    (progn
      (unload_dialog dclId)
      (princ "\n[-] Error: Dialog definition 'r_layer_selector_dialog' not found in DCL.")
      (exit)
    )
  )

  ;; Populate layers listbox
  (start_list "lst_layers")
  (mapcar 'add_list rLayers)
  (end_list)

  ;; Populate Linetypes dropdown
  (start_list "pop_layer_ltype")
  (mapcar 'add_list ltList)
  (end_list)

  ;; Populate Lineweights dropdown
  (start_list "pop_layer_lweight")
  (mapcar 'add_list lwLabels)
  (end_list)

  ;; Initial selection state
  (setq selIdx (if (and *WF-LAYER-RL* (vl-position *WF-LAYER-RL* rLayers))
                 (vl-position *WF-LAYER-RL* rLayers)
                 0))
  (setq selLayer (nth selIdx rLayers))
  (set_tile "lst_layers" (itoa selIdx))

  ;; Details Updater Subroutine
  (defun updateDetails (layName / obj cVal ltp lwt plt dbRow desc swW swH posLtp posLwt descLines pendT)
    (setq obj (vl-catch-all-apply 'vla-item (list layersColl layName)))
    (if (and (not (vl-catch-all-error-p obj)) (= (type obj) 'VLA-OBJECT))
      (progn
        (setq layObj obj)
        (setq cVal (abs (vla-get-color layObj)))
        (setq curCol cVal)
        (setq ltp (vla-get-linetype layObj))
        (setq lwt (vla-get-lineweight layObj))
        (setq plt (= (vla-get-plottable layObj) :vlax-true))

        ;; Render Color Swatch
        (setq swW (dimx_tile "img_color_swatch")
              swH (dimy_tile "img_color_swatch"))
        (start_image "img_color_swatch")
        (fill_image 0 0 swW swH cVal)
        (end_image)

        ;; Update textual tiles
        (set_tile "txt_layer_name" (strcat "Layer: " layName))
        (set_tile "txt_layer_color" (strcat "Color: " (itoa cVal) " (ACI)"))

        ;; Match and set Linetype popup
        (setq posLtp (vl-position (strcase ltp) (mapcar 'strcase ltList)))
        (if posLtp (set_tile "pop_layer_ltype" (itoa posLtp)))

        ;; Match and set Lineweight popup
        (setq posLwt (vl-position lwt lwValues))
        (if (null posLwt) (setq posLwt 0))
        (set_tile "pop_layer_lweight" (itoa posLwt))

        ;; Set Plottable toggle
        (set_tile "tog_layer_plot" (if plt "1" "0"))

        ;; Read transparency from pending map or default DB
        (setq pendT (assoc layName pendingTransMap))
        (if pendT
          (setq curTrans (cdr pendT))
          (progn
            (setq dbRow (assoc (strcase layName) *CadSetup-Layers-Data*))
            (setq curTrans (if (and dbRow (numberp (nth 9 dbRow))) (nth 9 dbRow) 0))
          )
        )
        (set_tile "eb_layer_trans" (itoa curTrans))

        ;; Associated Hatch Specs
        (setq dbRow (assoc (strcase layName) *CadSetup-Layers-Data*))
        (if dbRow
          (progn
            (setq curHPat  (if (nth 6 dbRow) (vl-princ-to-string (nth 6 dbRow)) "NONE")
                  curHScl  (if (numberp (nth 7 dbRow)) (nth 7 dbRow) 1.0)
                  curHRot  (if (numberp (nth 8 dbRow)) (nth 8 dbRow) 0.0))
            (set_tile "eb_hatch_pat" curHPat)
            (set_tile "eb_hatch_scl" (rtos curHScl 2 2))
            (set_tile "eb_hatch_rot" (rtos curHRot 2 1))
          )
          (progn
            (setq curHPat "NONE" curHScl 1.0 curHRot 0.0)
            (set_tile "eb_hatch_pat" "NONE")
            (set_tile "eb_hatch_scl" "1.0")
            (set_tile "eb_hatch_rot" "0.0")
          )
        )

        ;; Fetch Description from Db_Layers and wrap across 3 lines
        (setq desc (if (and dbRow (nth 11 dbRow)) (vl-princ-to-string (nth 11 dbRow)) ""))
        (setq descLines (CadSetup:WrapText3Lines desc 50))
        (set_tile "txt_layer_desc1" (nth 0 descLines))
        (set_tile "txt_layer_desc2" (nth 1 descLines))
        (set_tile "txt_layer_desc3" (nth 2 descLines))
      )
    )
  )

  ;; Initial view population
  (updateDetails selLayer)

  ;; Event Handlers
  (action_tile "lst_layers"
    "(setq selIdx (atoi $value)
           selLayer (nth selIdx rLayers))
     (updateDetails selLayer)
     (if (= $reason 4)
       (done_dialog 1)
     )"
  )

  (action_tile "btn_edit_color"
    "(if layObj
       (progn
         (setq newCol (acad_colordlg curCol nil))
         (if (and newCol (numberp newCol))
           (progn
             (vla-put-color layObj newCol)
             (setq curCol newCol)
             (updateDetails selLayer)
           )
         )
       )
     )"
  )

  (action_tile "pop_layer_ltype"
    "(if layObj
       (progn
         (setq selLtypeIdx (atoi $value))
         (if (and (>= selLtypeIdx 0) (< selLtypeIdx (length ltList)))
           (vl-catch-all-apply 'vla-put-linetype (list layObj (nth selLtypeIdx ltList)))
         )
       )
     )"
  )

  (action_tile "pop_layer_lweight"
    "(if layObj
       (progn
         (setq selLwIdx (atoi $value))
         (if (and (>= selLwIdx 0) (< selLwIdx (length lwValues)))
           (vl-catch-all-apply 'vla-put-lineweight (list layObj (nth selLwIdx lwValues)))
         )
       )
     )"
  )

  (action_tile "tog_layer_plot"
    "(if layObj
       (vla-put-plottable layObj (if (= $value \"1\") :vlax-true :vlax-false))
     )"
  )

  (action_tile "eb_layer_trans"
    "(setq rawVal (atoi $value))
     (if (and (>= rawVal 0) (<= rawVal 90))
       (progn
         (setq curTrans rawVal)
         (setq pendingTransMap (cons (cons selLayer curTrans) 
                                     (vl-remove-if (function (lambda (x) (= (car x) selLayer))) pendingTransMap)))
         (CadSetup:UpdateLayerDataInMemory selLayer nil nil nil curTrans)
       )
       (set_tile \"eb_layer_trans\" (itoa curTrans))
     )"
  )

  (action_tile "eb_hatch_pat"
    "(if (and $value (/= $value \"\"))
       (progn
         (setq curHPat (strcase $value))
         (CadSetup:UpdateLayerDataInMemory selLayer curHPat nil nil nil)
       )
     )"
  )

  (action_tile "eb_hatch_scl"
    "(setq rawScl (distof $value))
     (if (and rawScl (> rawScl 0.0))
       (progn
         (setq curHScl rawScl)
         (CadSetup:UpdateLayerDataInMemory selLayer nil curHScl nil nil)
       )
       (set_tile \"eb_hatch_scl\" (rtos curHScl 2 2))
     )"
  )

  (action_tile "eb_hatch_rot"
    "(setq rawScl (distof $value))
     (if rawScl
       (progn
         (setq curHRot rawScl)
         (CadSetup:UpdateLayerDataInMemory selLayer nil nil curHRot nil)
       )
       (set_tile \"eb_hatch_rot\" (rtos curHRot 2 1))
     )"
  )

  (action_tile "btn_reset_defaults"
    "(if (boundp '*CadSetup-Master-Layers-Backup*)
       (setq defRow (assoc (strcase selLayer) *CadSetup-Master-Layers-Backup*))
       (setq defRow nil)
     )
     (if defRow
       (progn
         (setq defCol   (if (numberp (nth 1 defRow)) (nth 1 defRow) 7)
               defLt    (if (nth 3 defRow) (vl-princ-to-string (nth 3 defRow)) \"CONTINUOUS\")
               defLw    (if (numberp (nth 4 defRow)) (nth 4 defRow) 25)
               defPlot  (nth 5 defRow)
               defPat   (if (nth 6 defRow) (vl-princ-to-string (nth 6 defRow)) \"NONE\")
               defScl   (if (numberp (nth 7 defRow)) (nth 7 defRow) 1.0)
               defRot   (if (numberp (nth 8 defRow)) (nth 8 defRow) 0.0)
               defTrans (if (numberp (nth 9 defRow)) (nth 9 defRow) 0))

         (if layObj
           (progn
             (vla-put-color layObj defCol)
             (vl-catch-all-apply 'vla-put-linetype (list layObj defLt))
             (vl-catch-all-apply 'vla-put-lineweight (list layObj defLw))
             (vla-put-plottable layObj (if defPlot :vlax-true :vlax-false))
           )
         )
         (setq curTrans defTrans)
         (setq pendingTransMap (cons (cons selLayer curTrans) 
                                     (vl-remove-if (function (lambda (x) (= (car x) selLayer))) pendingTransMap)))
         (CadSetup:UpdateLayerDataInMemory selLayer defPat defScl defRot defTrans)
         (updateDetails selLayer)
         (princ (strcat \"\\n[-] Reset \" selLayer \" to standard database defaults.\"))
       )
       (princ (strcat \"\\n[-] No default definition found for \" selLayer))
     )"
  )

  (action_tile "btn_draw_pl" "(done_dialog 1)")
  (action_tile "btn_draw_rec" "(done_dialog 2)")
  (action_tile "btn_current" "(done_dialog 3)")
  (action_tile "cancel" "(done_dialog 0)")

  (setq act (start_dialog))
  (unload_dialog dclId)

  ;; Apply any modified layer transparencies natively outside DCL
  (if pendingTransMap
    (progn
      (setq oldEcho (getvar "CMDECHO"))
      (setvar "CMDECHO" 0)
      (foreach item pendingTransMap
        (vl-catch-all-apply
          (function (lambda ()
            (command "._-LAYER" "_TR" (itoa (cdr item)) (car item) "")
          ))
        )
      )
      (setvar "CMDECHO" oldEcho)
    )
  )

  ;; Return action result: (list actionType layerName)
  (cond
    ((= act 1) (list :draw-pl selLayer))
    ((= act 2) (list :draw-rec selLayer))
    ((= act 3) (list :current selLayer))
    (t nil)
  )
)

;; c:` Main Entry Point for Workflow Key '`' (R-Layers)
(defun c:` ( / ss *error* rLayers ans promptStr kwStr kwMap suffix kw opt res chosenLayer loopPrompt )
  (setq ss (ssget "_I"))
  (if (and ss (> (sslength ss) 0))
    (CadSetup:PromptAndAssignLayer ss "R-*" "R-Layer" T)
    (progn
      (defun *error* (msg)
        (if (boundp 'CadSetup:UndoReset) (CadSetup:UndoReset))
        (if (and msg (not (wcmatch (strcase msg t) "*break*,*cancel*,*exit*")))
          (princ (strcat "\n[-] Error: " msg))
        )
        (princ)
      )

      ;; 1. Check for existing R-* layers in active drawing
      (setq rLayers (CadSetup:GetDrawingRLayers))

      (if (null rLayers)
        (CadSetup:OpenLayerSelector "R-*" "All R-* Layers Selection && Property Inspector" nil T)
        (progn
          (if (null *WF-TOOL-RL*) (setq *WF-TOOL-RL* "Polyline"))

          (setq loopPrompt t)
          (while loopPrompt
            (setq kwMap '(("DIALOG" . "DIALOG") ("D" . "DIALOG")
                          ("PL" . :TOOL-PL) ("POLYLINE" . :TOOL-PL)
                          ("REC" . :TOOL-REC) ("RECTANGLE" . :TOOL-REC)))
            (setq promptStr (strcat "\nSelect R-Layer (" *WF-TOOL-RL* ") [Dialog/PL/REC"))
            (setq kwStr "Dialog D PL Polyline REC Rectangle")

            (foreach lay rLayers
              (setq suffix (if (> (strlen lay) 2) (substr lay 3) lay))
              (setq kw (strcase (vl-string-translate " " "_" suffix)))
              (setq kwMap (cons (cons kw lay) kwMap))
              (setq promptStr (strcat promptStr "/" suffix))
              (setq kwStr (strcat kwStr " " kw))
            )
            (setq promptStr (strcat promptStr "] <Dialog>: "))

            (initget kwStr)
            (setq opt (getkword promptStr))

            (cond
              ((or (equal opt "PL") (equal (and opt (strcase opt)) "POLYLINE"))
               (setq *WF-TOOL-RL* "Polyline")
               (princ "\n[-] Default drawing tool switched to: Polyline")
              )

              ((or (equal opt "REC") (equal (and opt (strcase opt)) "RECTANGLE"))
               (setq *WF-TOOL-RL* "Rectangle")
               (princ "\n[-] Default drawing tool switched to: Rectangle")
              )

              ((or (null opt) (= (strcase opt) "DIALOG") (= (strcase opt) "D"))
               (setq loopPrompt nil)
               (CadSetup:OpenLayerSelector "R-*" "All R-* Layers Selection && Property Inspector" nil T)
              )

              (t
               (setq loopPrompt nil)
               (setq chosenLayer (cdr (assoc (strcase (vl-string-translate " " "_" opt)) kwMap)))
               (if chosenLayer
                 (progn
                   (CadSetup:SetCurrentLayerSafe chosenLayer)
                   (setq *WF-LAYER-RL* chosenLayer)
                   (if (equal (strcase (if *WF-TOOL-RL* *WF-TOOL-RL* "Polyline")) "RECTANGLE")
                     (CadSetup:DrawRectangle chosenLayer)
                     (CadSetup:DrawPolyline chosenLayer)
                   )
                 )
                 (princ (strcat "\n[-] Unrecognized option: " opt))
               )
              )
            )
          )
        )
      )
    )
  )
  (princ)
)

;; Command Aliases for Workflow Key '`'
(defun c:-    () (c:`))
(defun c:R-   () (c:`))
(defun c:RLAY () (c:`))


(if *CadSetup-Debug*
  (princ "\n[01_Workflow-Keys.lsp] Workflow keys (0=L0, 1=HL, 2=VP, 3=GL, 4=LL, 5=ML, 6=AD, 7=HD, 8=BL, `=R-) loaded.")
)
(princ)
